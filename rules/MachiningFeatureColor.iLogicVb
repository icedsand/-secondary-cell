' 가공 형상 색상 (made by pjh)

Sub Main()

    Dim PREFIXES As String = "GMKS-"              ' 가공품 번호 접두어 (쉼표로 여러 개)
    Dim MAX_REV_LETTERS As Integer = 2            ' 번호 끝 리비전 문자 최대 개수
    Dim SUFFIXES As String = "_MIR"               ' 떼고 볼 번호 꼬리 (쉼표로 여러 개)

    Dim C_DRILL  As String = "파랑:0,112,255"     ' 색상 "이름:R,G,B"
    Dim C_CBORE  As String = "주황:255,128,0"
    Dim C_CSINK  As String = "초록:0,176,80"
    Dim C_SPOT   As String = "보라:150,60,220"
    Dim C_TAP    As String = "빨강:230,0,0"
    Dim C_THREAD As String = "노랑:255,210,0"

    Dim TAP_OVER_TYPE As Boolean = True           ' 탭 구멍은 종류와 관계없이 탭 색
    Dim SHOW_THROUGH_ASM_COLOR As Boolean = True  ' 조립도에서 덮어쓴 색을 임시 뷰 표현에서 풀기
    Dim KEEP_CLEAN As Boolean = True              ' 칠한 부품을 저장하라고 묻지 않게
    Dim LIST_MAX As Integer = 12                  ' 결과 창 목록 최대 줄 수

    Dim TTL As String = "가공 형상 색상"

    Dim doc As Inventor.Document = ThisApplication.ActiveDocument
    If doc Is Nothing Then
        MessageBox.Show("열린 문서가 없습니다.", TTL)
        Return
    End If

    Dim ans As DialogResult = MessageBox.Show( _
        "무엇을 할까요?" & vbCrLf & vbCrLf & _
        "[예]       가공품의 구멍·나사에 색 칠하기" & vbCrLf & _
        "[아니오]   원래 색으로 되돌리기" & vbCrLf & _
        "[취소]     그만두기", _
        TTL, MessageBoxButtons.YesNoCancel, MessageBoxIcon.Question)

    If ans = DialogResult.Yes Then

        If doc.DocumentType <> DocumentTypeEnum.kAssemblyDocumentObject AndAlso _
           doc.DocumentType <> DocumentTypeEnum.kPartDocumentObject Then
            MessageBox.Show("조립도나 부품을 열고 실행하세요.", TTL)
            Return
        End If

        Dim rgbs(5, 2) As Integer
        Dim cNames(5) As String
        SetColor(rgbs, cNames, 0, C_DRILL)
        SetColor(rgbs, cNames, 1, C_CBORE)
        SetColor(rgbs, cNames, 2, C_CSINK)
        SetColor(rgbs, cNames, 3, C_SPOT)
        SetColor(rgbs, cNames, 4, C_TAP)
        SetColor(rgbs, cNames, 5, C_THREAD)

        PaintMode(doc, SplitPrefixes(PREFIXES), MAX_REV_LETTERS, SplitPrefixes(SUFFIXES), rgbs, cNames, _
                  TAP_OVER_TYPE, SHOW_THROUGH_ASM_COLOR, KEEP_CLEAN, LIST_MAX, TTL)

    ElseIf ans = DialogResult.No Then

        RestoreMode(KEEP_CLEAN, LIST_MAX, TTL)

    End If

End Sub


Sub PaintMode(top As Inventor.Document, prefixes As List(Of String), maxRev As Integer, _
              suffixes As List(Of String), _
              rgbs As Integer(,), cNames As String(), tapWins As Boolean, _
              showThrough As Boolean, keepClean As Boolean, listMax As Integer, TTL As String)

    Dim targets As New List(Of PartDocument)
    Dim skipNames As New List(Of String)

    If top.DocumentType = DocumentTypeEnum.kPartDocumentObject Then

        targets.Add(CType(top, PartDocument))

    Else

        For Each d As Inventor.Document In top.AllReferencedDocuments

            If d.DocumentType <> DocumentTypeEnum.kPartDocumentObject Then Continue For

            Dim pd As PartDocument = CType(d, PartDocument)

            If IsContentPart(pd) Then Continue For

            Dim pn As String = ReadPN(d)
            Dim fn As String = FileTitle(d)

            If IsMachinedNo(pn, prefixes, maxRev, suffixes) OrElse IsMachinedNo(fn, prefixes, maxRev, suffixes) Then
                targets.Add(pd)
            Else
                skipNames.Add(DocLabel(d))
            End If
        Next

    End If

    skipNames.Sort(StringComparer.OrdinalIgnoreCase)

    If targets.Count = 0 Then
        MessageBox.Show("가공품 번호 규칙에 맞는 부품이 없습니다." & vbCrLf & vbCrLf & _
                        "   지금 규칙 : " & RuleText(prefixes, maxRev, suffixes) & vbCrLf & vbCrLf & _
                        "제외된 부품 (" & skipNames.Count & "개)" & vbCrLf & _
                        ListLines(skipNames, listMax) & vbCrLf & _
                        "번호 규칙이 다르면 rule 위쪽 설정의 PREFIXES 를 고치세요.", TTL)
        Return
    End If

    Dim covered As New List(Of ComponentOccurrence)

    If showThrough AndAlso top.DocumentType = DocumentTypeEnum.kAssemblyDocumentObject Then

        Dim tPaths As New HashSet(Of String)(StringComparer.OrdinalIgnoreCase)
        For Each pd As PartDocument In targets
            tPaths.Add(DocPath(pd))
        Next

        Dim asmDoc As AssemblyDocument = CType(top, AssemblyDocument)

        For Each occ As ComponentOccurrence In asmDoc.ComponentDefinition.Occurrences.AllLeafOccurrences
            Try
                If occ.Suppressed Then Continue For
                If Not tPaths.Contains(occ.ReferencedDocumentDescriptor.FullDocumentName) Then Continue For
                If IsColorCovered(occ) Then covered.Add(occ)
            Catch
            End Try
        Next

    End If

    Dim counts(5) As Integer
    Dim faceCount As Integer = 0
    Dim failCount As Integer = 0
    Dim paintedParts As Integer = 0
    Dim mixed As New List(Of String)
    Dim errs As New List(Of String)
    Dim cleanList As New List(Of Inventor.Document)
    Dim occShown As Integer = 0
    Dim occStill As Integer = 0
    Dim stillNames As New List(Of String)
    Dim dvrFail As Boolean = False

    Dim topWasClean As Boolean = Not IsDirtyDoc(top)
    Dim wasClean As New List(Of Boolean)
    For Each pd As PartDocument In targets
        wasClean.Add(Not IsDirtyDoc(pd))
    Next

    Dim sw As New System.Diagnostics.Stopwatch()
    sw.Start()

    Dim prevSilent As Boolean = ThisApplication.SilentOperation
    Dim prevScreen As Boolean = ThisApplication.ScreenUpdating
    Dim tx As Transaction = Nothing
    Dim pb As Inventor.ProgressBar = MakeProgress(targets.Count + 1, TTL & " - 칠하는 중")

    Try
        ThisApplication.SilentOperation = True
        ThisApplication.ScreenUpdating = False

        Try
            tx = ThisApplication.TransactionManager.StartGlobalTransaction(top, "가공 형상 색칠")
        Catch
            tx = Nothing
        End Try

        For i As Integer = 0 To targets.Count - 1

            Dim pd As PartDocument = targets(i)
            StepProgress(pb, (i + 1) & " / " & targets.Count & "   " & FileTitle(pd))

            Dim before As Integer = faceCount
            Dim faceMarked As Boolean = False
            Try
                MarkDoc(pd, "HFC_DOC")
                PaintPart(pd, rgbs, tapWins, counts, faceCount, failCount, mixed, faceMarked, errs)
                If faceMarked Then FlagFaces(pd)
            Catch ex As Exception
                failCount += 1
                AddErr(errs, "부품 처리", ex.Message, pd)
            End Try

            If faceCount > before Then paintedParts += 1
            If keepClean AndAlso wasClean(i) Then cleanList.Add(pd)
        Next

    Finally
        If tx IsNot Nothing Then
            Try
                tx.End()
            Catch
            End Try
        End If
    End Try

    Try
        If covered.Count > 0 Then

            StepProgress(pb, "조립도 색 덮어쓰기 푸는 중")

            Dim asmDoc As AssemblyDocument = CType(top, AssemblyDocument)

            If ActivateTempDvr(asmDoc) Then

                Dim doneKeys As New HashSet(Of String)(StringComparer.OrdinalIgnoreCase)
                For Each occ As ComponentOccurrence In covered
                    ClearCoverChain(occ, doneKeys)
                Next

                For Each occ As ComponentOccurrence In covered
                    If IsColorCovered(occ) Then
                        occStill += 1
                        If stillNames.Count < 200 Then stillNames.Add(OccKey(occ))
                    Else
                        occShown += 1
                    End If
                Next
            Else
                dvrFail = True
                occStill = covered.Count
            End If

        End If

    Finally
        ThisApplication.ScreenUpdating = prevScreen
        ThisApplication.SilentOperation = prevSilent
        CloseProgress(pb)
    End Try

    If keepClean AndAlso topWasClean AndAlso Not cleanList.Contains(top) Then cleanList.Add(top)

    For Each d As Inventor.Document In cleanList
        Try
            d.Dirty = False
        Catch
        End Try
    Next

    Try
        ThisApplication.ActiveView.Update()
    Catch
    End Try

    Dim res As String = "색칠을 마쳤습니다." & vbCrLf & vbCrLf & _
                        "   칠한 가공품 : " & paintedParts & " / " & targets.Count & "개" & vbCrLf & _
                        "   칠한 면     : " & faceCount & "개" & vbCrLf & _
                        "   걸린 시간   : " & ElapsedText(sw) & vbCrLf & vbCrLf

    For k As Integer = 0 To 5
        res &= "   " & ClassLabel(k).PadRight(6) & " (" & cNames(k) & ")  : 피처 " & counts(k) & "개" & vbCrLf
    Next
    res &= vbCrLf

    If mixed.Count > 0 Then
        res &= "아래 패턴/미러는 여러 피처가 섞여 있는데, 원본 구멍 면과 같은 면을" & vbCrLf & _
               "찾지 못해 칠하지 않았습니다." & vbCrLf & ListLines(mixed, listMax) & vbCrLf
    End If

    If failCount > 0 Then
        res &= "칠하지 못한 면 : " & failCount & "개" & vbCrLf & vbCrLf
    End If

    If errs.Count > 0 Then
        res &= "실패 이유 (인벤터 오류 메시지 - 이 화면을 그대로 알려주세요)" & vbCrLf & _
               ListLines(errs, 6) & vbCrLf
    End If

    If covered.Count > 0 Then
        If dvrFail Then
            res &= "임시 뷰 표현을 만들지 못해, 조립도에서 색을 덮어쓴 가공품 " & covered.Count & "개는" & vbCrLf & _
                   "색이 보이지 않을 수 있습니다." & vbCrLf & vbCrLf
        Else
            res &= "뷰 표현 """ & TempDvrName() & """ 에서 조립도 색 덮어쓰기를 풀었습니다 : " & occShown & "개" & vbCrLf
            If occStill > 0 Then
                res &= "   풀지 못함 : " & occStill & "개 (색이 안 보임)" & vbCrLf & _
                       ListLines(stillNames, listMax)
            End If
            res &= vbCrLf
        End If
    End If

    res &= "부품은 저장하지 않았습니다." & vbCrLf & _
           "★ 색이 칠해진 채로 부품을 고치고 저장하면 색도 같이 저장됩니다." & vbCrLf & _
           "   부품을 고치기 전에 [원래대로] 를 먼저 실행하세요."

    MessageBox.Show(res, TTL)

End Sub


Sub RestoreMode(keepClean As Boolean, listMax As Integer, TTL As String)

    Dim parts As New List(Of PartDocument)
    Dim asms As New List(Of AssemblyDocument)

    Dim top As Inventor.Document = ThisApplication.ActiveDocument
    Dim scope As New List(Of Inventor.Document)
    Dim scopePaths As New HashSet(Of String)(StringComparer.OrdinalIgnoreCase)
    scope.Add(top)
    scopePaths.Add(DocPath(top))
    Try
        For Each d As Inventor.Document In top.AllReferencedDocuments
            scope.Add(d)
            scopePaths.Add(DocPath(d))
        Next
    Catch
    End Try

    For Each d As Inventor.Document In scope
        Try
            If d.DocumentType = DocumentTypeEnum.kPartDocumentObject Then
                Dim pd As PartDocument = CType(d, PartDocument)
                If HasPartMarks(pd) Then parts.Add(pd)
            ElseIf d.DocumentType = DocumentTypeEnum.kAssemblyDocumentObject Then
                If d.AttributeSets.NameIsUsed("HFC_ASM") Then asms.Add(CType(d, AssemblyDocument))
            End If
        Catch
        End Try
    Next

    Dim otherCount As Integer = 0
    For Each d As Inventor.Document In SnapshotDocs()
        Try
            If scopePaths.Contains(DocPath(d)) Then Continue For
            If d.DocumentType = DocumentTypeEnum.kPartDocumentObject Then
                If HasPartMarks(CType(d, PartDocument)) Then otherCount += 1
            End If
        Catch
        End Try
    Next

    Dim otherNote As String = ""
    If otherCount > 0 Then
        otherNote = "다른 조립도에만 들어 있는 칠한 부품 " & otherCount & "개는 건드리지 않았습니다." & vbCrLf & _
                    "그 조립도를 열고 [원래대로] 를 실행하세요." & vbCrLf & vbCrLf
    End If

    If parts.Count = 0 AndAlso asms.Count = 0 Then
        MessageBox.Show("지금 연 조립도에는 되돌릴 색이 없습니다." & vbCrLf & vbCrLf & otherNote, TTL)
        Return
    End If

    Dim nFaces As Integer = 0
    Dim nFail As Integer = 0
    Dim errs As New List(Of String)
    Dim nAsm As Integer = 0
    Dim asmFail As New List(Of String)
    Dim cleanList As New List(Of Inventor.Document)
    Dim savedList As New List(Of String)

    Dim partClean As New List(Of Boolean)
    For Each pd As PartDocument In parts
        Dim inMemoryOnly As Boolean = PaintedThisSession(pd, "HFC_DOC")
        If Not inMemoryOnly Then savedList.Add(DocLabel(pd))
        partClean.Add(keepClean AndAlso inMemoryOnly AndAlso Not IsDirtyDoc(pd))
    Next

    Dim asmClean As New List(Of Boolean)
    For Each asmDoc As AssemblyDocument In asms
        Dim inMemoryOnly As Boolean = PaintedThisSession(asmDoc, "HFC_ASM")
        If Not inMemoryOnly Then savedList.Add(DocLabel(asmDoc))
        asmClean.Add(keepClean AndAlso inMemoryOnly AndAlso Not IsDirtyDoc(asmDoc))
    Next

    Dim act As Inventor.Document = ThisApplication.ActiveDocument
    Dim actWasClean As Boolean = Not IsDirtyDoc(act)

    Dim sw As New System.Diagnostics.Stopwatch()
    sw.Start()

    Dim prevSilent As Boolean = ThisApplication.SilentOperation
    Dim prevScreen As Boolean = ThisApplication.ScreenUpdating
    Dim tx As Transaction = Nothing
    Dim pb As Inventor.ProgressBar = MakeProgress(parts.Count + asms.Count, TTL & " - 되돌리는 중")

    Try
        ThisApplication.SilentOperation = True
        ThisApplication.ScreenUpdating = False

        Try
            tx = ThisApplication.TransactionManager.StartGlobalTransaction( _
                     ThisApplication.ActiveDocument, "가공 형상 색 되돌리기")
        Catch
            tx = Nothing
        End Try

        For i As Integer = 0 To parts.Count - 1
            StepProgress(pb, (i + 1) & " / " & parts.Count & "   " & FileTitle(parts(i)))
            Try
                RestorePart(parts(i), nFaces, nFail, errs)
            Catch ex As Exception
                nFail += 1
                AddErr(errs, "부품 되돌리기", ex.Message, parts(i))
            End Try

            If partClean(i) Then cleanList.Add(parts(i))
        Next

    Finally
        If tx IsNot Nothing Then
            Try
                tx.End()
            Catch
            End Try
        End If
    End Try

    Try
        For i As Integer = 0 To asms.Count - 1
            StepProgress(pb, "조립도 뷰 표현 되돌리는 중   " & FileTitle(asms(i)))
            If RestoreAsm(asms(i)) Then
                nAsm += 1
            Else
                asmFail.Add(DocLabel(asms(i)))
            End If

            If asmClean(i) Then cleanList.Add(asms(i))
        Next

    Finally
        ThisApplication.ScreenUpdating = prevScreen
        ThisApplication.SilentOperation = prevSilent
        CloseProgress(pb)
    End Try

    Dim actIsTarget As Boolean = False
    For Each pd As PartDocument In parts
        If pd Is act Then actIsTarget = True
    Next
    For Each asmDoc As AssemblyDocument In asms
        If asmDoc Is act Then actIsTarget = True
    Next
    If keepClean AndAlso actWasClean AndAlso Not actIsTarget Then cleanList.Add(act)

    For Each d As Inventor.Document In cleanList
        Try
            d.Dirty = False
        Catch
        End Try
    Next

    Try
        ThisApplication.ActiveView.Update()
    Catch
    End Try

    Dim res As String = "원래 색으로 되돌렸습니다." & vbCrLf & vbCrLf & _
                        "   부품      : " & parts.Count & "개" & vbCrLf & _
                        "   피처/면   : " & nFaces & "개" & vbCrLf & _
                        "   걸린 시간 : " & ElapsedText(sw) & vbCrLf

    If asms.Count > 0 Then
        res &= "   조립도 뷰 표현 : " & nAsm & "개 원래대로" & vbCrLf
    End If
    res &= vbCrLf

    If nFail > 0 Then
        res &= "되돌리지 못한 피처/면 : " & nFail & "개" & vbCrLf & _
               "   [원래대로] 를 한 번 더 실행하면 남은 것만 다시 시도합니다." & vbCrLf & vbCrLf
    End If

    If errs.Count > 0 Then
        res &= "실패 이유 (인벤터 오류 메시지 - 이 화면을 그대로 알려주세요)" & vbCrLf & _
               ListLines(errs, 8) & vbCrLf
    End If

    If asmFail.Count > 0 Then
        res &= "원래 뷰 표현으로 돌아가지 못한 조립도입니다." & vbCrLf & _
               "모형 탐색기의 [표현 > 뷰] 에서 원래 뷰 표현을 직접 고르고" & vbCrLf & _
               """" & TempDvrName() & """ 을 지우세요." & vbCrLf & _
               ListLines(asmFail, listMax) & vbCrLf
    End If

    res &= otherNote

    If savedList.Count > 0 Then
        res &= "아래 문서는 칠한 색이 파일에 저장되어 있었습니다." & vbCrLf & _
               "저장해야 원래 색이 파일에도 반영됩니다." & vbCrLf & _
               ListLines(savedList, listMax)
    End If

    MessageBox.Show(res, TTL)

End Sub


Sub PaintPart(pd As PartDocument, rgbs As Integer(,), tapWins As Boolean, _
              counts As Integer(), ByRef faceCount As Integer, ByRef failCount As Integer, _
              mixed As List(Of String), ByRef faceMarked As Boolean, errs As List(Of String))

    Dim cd As PartComponentDefinition = pd.ComponentDefinition

    Dim nHole As Integer = 0
    Dim nThread As Integer = 0
    Try
        nHole = cd.Features.HoleFeatures.Count
        nThread = cd.Features.ThreadFeatures.Count
    Catch
        nHole = 1
    End Try
    If nHole = 0 AndAlso nThread = 0 Then Return

    Dim cache(5) As Asset
    Dim retried(5) As Boolean

    For pass As Integer = 1 To 2

        If pass = 2 AndAlso nThread = 0 Then Exit For

        For Each o As Object In cd.Features

            Dim f As PartFeature = TryCast(o, PartFeature)
            If f Is Nothing Then Continue For

            Dim k As Integer
            Dim faceList As Object = Nothing

            If TypeOf f Is HoleFeature Then
                If pass <> 1 Then Continue For
                If IsSuppressedFeature(f) Then Continue For
                k = HoleClass(CType(f, HoleFeature), tapWins)
                faceList = f.Faces

            ElseIf TypeOf f Is ThreadFeature Then
                If pass <> 2 Then Continue For
                If IsSuppressedFeature(f) Then Continue For
                k = 5
                faceList = ThreadFaces(CType(f, ThreadFeature))

            ElseIf IsPatternType(f) Then
                If IsSuppressedFeature(f) Then Continue For
                k = PatternClass(f, tapWins, 0)
                If k = -1 Then Continue For
                If k = -2 Then
                    If pass = 1 Then
                        Dim nMix As Integer = PaintMixedPattern(pd, f, tapWins, rgbs, cache, counts, _
                                                                 faceCount, failCount, errs)
                        If nMix > 0 Then
                            faceMarked = True
                        Else
                            mixed.Add(FileTitle(pd) & " : " & f.Name)
                        End If
                    End If
                    Continue For
                End If
                If (k = 5) <> (pass = 2) Then Continue For
                faceList = f.Faces

            Else
                Continue For
            End If

            If cache(k) Is Nothing Then cache(k) = GetAsset(pd, k, rgbs, False, errs)

            Dim failBefore As Integer = failCount
            Dim n As Integer = PaintWith(pd, f, k, faceList, cache(k), failCount, faceMarked, errs)

            If n = 0 AndAlso failCount > failBefore AndAlso Not retried(k) Then
                retried(k) = True
                Dim fresh As Asset = GetAsset(pd, k, rgbs, True, errs)
                If fresh IsNot Nothing Then
                    cache(k) = fresh
                    failCount = failBefore
                    n = PaintWith(pd, f, k, faceList, cache(k), failCount, faceMarked, errs)
                End If
            End If

            If n > 0 Then
                counts(k) += 1
                faceCount += n
            End If
        Next
    Next

End Sub


Function HoleClass(h As HoleFeature, tapWins As Boolean) As Integer

    Dim t As Integer = 0
    Try
        Select Case h.HoleType
            Case HoleTypeEnum.kCounterBoreHole : t = 1
            Case HoleTypeEnum.kCounterSinkHole : t = 2
            Case HoleTypeEnum.kSpotFaceHole    : t = 3
            Case Else                          : t = 0
        End Select
    Catch
        t = 0
    End Try

    Dim tapped As Boolean = False
    Try
        tapped = h.Tapped
    Catch
        tapped = False
    End Try

    If tapped AndAlso (tapWins OrElse t = 0) Then Return 4
    Return t

End Function


Function PatternClass(f As PartFeature, tapWins As Boolean, depth As Integer) As Integer

    If depth > 8 Then Return -1

    If TypeOf f Is HoleFeature Then Return HoleClass(CType(f, HoleFeature), tapWins)
    If TypeOf f Is ThreadFeature Then Return 5
    If Not IsPatternType(f) Then Return -1

    Dim parents As Object = Nothing
    Try
        Dim lf As Object = f
        parents = lf.ParentFeatures
    Catch
        Return -1
    End Try
    If parents Is Nothing Then Return -1

    Dim found As Integer = -1
    Dim hasOther As Boolean = False
    Dim hasThread As Boolean = False
    Dim differ As Boolean = False

    For Each p As Object In parents

        Dim pf As PartFeature = TryCast(p, PartFeature)
        Dim c As Integer = -1
        If pf IsNot Nothing Then c = PatternClass(pf, tapWins, depth + 1)

        If c = -2 Then Return -2

        If c = 5 Then
            hasThread = True
        ElseIf c = -1 Then
            hasOther = True
        ElseIf found = -1 Then
            found = c
        ElseIf found <> c Then
            differ = True
        End If
    Next

    If found = -1 Then
        If hasThread AndAlso Not hasOther Then Return 5
        Return -1
    End If

    If hasOther OrElse differ OrElse hasThread Then Return -2
    Return found

End Function


Function PaintMixedPattern(pd As PartDocument, f As PartFeature, tapWins As Boolean, _
                           rgbs As Integer(,), cache As Asset(), counts As Integer(), _
                           ByRef faceCount As Integer, ByRef failCount As Integer, _
                           errs As List(Of String)) As Integer

    Dim sigType As New List(Of Integer)
    Dim sigArea As New List(Of Double)
    Dim sigCls As New List(Of Integer)

    CollectSigs(f, tapWins, sigType, sigArea, sigCls, 0)
    If sigType.Count = 0 Then Return 0

    Dim groups(5) As List(Of Object)
    Try
        For Each o As Object In f.Faces
            Dim fc As Face = TryCast(o, Face)
            If fc Is Nothing Then Continue For
            Dim c As Integer = MatchSig(fc, sigType, sigArea, sigCls)
            If c < 0 Then Continue For
            If groups(c) Is Nothing Then groups(c) = New List(Of Object)
            groups(c).Add(fc)
        Next
    Catch ex As Exception
        AddErr(errs, "섞인 패턴 면 읽기", ex.Message, pd)
    End Try

    Dim total As Integer = 0
    For c As Integer = 0 To 5
        If groups(c) Is Nothing Then Continue For
        If cache(c) Is Nothing Then cache(c) = GetAsset(pd, c, rgbs, False, errs)
        Dim n As Integer = PaintFaces(pd, groups(c), cache(c), failCount, errs)
        If n > 0 Then
            counts(c) += 1
            faceCount += n
            total += n
        End If
    Next

    Return total

End Function


Sub CollectSigs(f As PartFeature, tapWins As Boolean, sigType As List(Of Integer), _
                sigArea As List(Of Double), sigCls As List(Of Integer), depth As Integer)

    If depth > 8 Then Return

    Dim parents As Object = Nothing
    Try
        Dim lf As Object = f
        parents = lf.ParentFeatures
    Catch
        Return
    End Try
    If parents Is Nothing Then Return

    For Each p As Object In parents
        Dim pf As PartFeature = TryCast(p, PartFeature)
        If pf Is Nothing Then Continue For

        Try
            If TypeOf pf Is HoleFeature Then
                AddSigs(pf.Faces, HoleClass(CType(pf, HoleFeature), tapWins), sigType, sigArea, sigCls)
            ElseIf TypeOf pf Is ThreadFeature Then
                AddSigs(ThreadFaces(CType(pf, ThreadFeature)), 5, sigType, sigArea, sigCls)
            ElseIf IsPatternType(pf) Then
                CollectSigs(pf, tapWins, sigType, sigArea, sigCls, depth + 1)
            End If
        Catch
        End Try
    Next

End Sub


Sub AddSigs(faceList As Object, c As Integer, sigType As List(Of Integer), _
            sigArea As List(Of Double), sigCls As List(Of Integer))

    If faceList Is Nothing Then Return

    For Each o As Object In faceList
        Dim fc As Face = TryCast(o, Face)
        If fc Is Nothing Then Continue For
        Try
            Dim t As Integer = CInt(fc.SurfaceType)
            Dim ar As Double = fc.Evaluator.Area
            sigType.Add(t)
            sigArea.Add(ar)
            sigCls.Add(c)
        Catch
        End Try
    Next

End Sub


Function MatchSig(fc As Face, sigType As List(Of Integer), sigArea As List(Of Double), _
                  sigCls As List(Of Integer)) As Integer

    Dim t As Integer
    Dim ar As Double
    Try
        t = CInt(fc.SurfaceType)
        ar = fc.Evaluator.Area
    Catch
        Return -1
    End Try

    Dim tol As Double = Math.Max(0.000000001, Math.Abs(ar) * 0.0001)
    Dim best As Integer = -1

    For i As Integer = 0 To sigType.Count - 1
        If sigType(i) <> t Then Continue For
        If Math.Abs(sigArea(i) - ar) > tol Then Continue For
        If sigCls(i) = 5 Then Return 5
        If best = -1 Then best = sigCls(i)
    Next

    Return best

End Function


Function IsPatternType(f As PartFeature) As Boolean
    Return TypeOf f Is RectangularPatternFeature OrElse _
           TypeOf f Is CircularPatternFeature OrElse _
           TypeOf f Is SketchDrivenPatternFeature OrElse _
           TypeOf f Is MirrorFeature
End Function


Function IsSuppressedFeature(f As PartFeature) As Boolean
    Try
        Return f.Suppressed
    Catch
        Return False
    End Try
End Function


Function ThreadFaces(tf As ThreadFeature) As List(Of Object)

    Dim res As New List(Of Object)

    Try
        Dim lf As Object = tf
        Dim tfc As Object = lf.ThreadedFace
        If tfc IsNot Nothing Then
            If TypeOf tfc Is Face Then
                res.Add(tfc)
            Else
                For Each o As Object In tfc
                    res.Add(o)
                Next
            End If
        End If
    Catch
    End Try

    If res.Count = 0 Then
        Try
            For Each o As Object In tf.Faces
                res.Add(o)
            Next
        Catch
        End Try
    End If

    Return res

End Function


Function PaintWith(pd As PartDocument, f As PartFeature, k As Integer, faceList As Object, a As Asset, _
                   ByRef failCount As Integer, ByRef faceMarked As Boolean, errs As List(Of String)) As Integer
    If k = 5 Then
        Dim n As Integer = PaintFaces(pd, faceList, a, failCount, errs)
        If n > 0 Then faceMarked = True
        Return n
    End If
    Return PaintFeature(pd, f, faceList, a, failCount, faceMarked, errs)
End Function


Function PaintFeature(pd As PartDocument, f As PartFeature, faceList As Object, a As Asset, _
                      ByRef failCount As Integer, ByRef faceMarked As Boolean, _
                      errs As List(Of String)) As Integer

    If faceList Is Nothing Then Return 0

    Dim nFace As Integer = 0
    Dim covered As New List(Of Object)

    For Each o As Object In faceList
        Dim fc As Face = TryCast(o, Face)
        If fc Is Nothing Then Continue For
        nFace += 1
        Try
            If fc.AppearanceSourceType = AppearanceSourceTypeEnum.kOverrideAppearance Then covered.Add(fc)
        Catch
        End Try
    Next

    If nFace = 0 Then Return 0

    If a Is Nothing Then
        failCount += nFace
        Return 0
    End If

    Dim featOk As Boolean = False
    Try
        SaveOriginal(f, "HFC_FEAT")
        f.Appearance = a
        Dim srcNow As Integer = CInt(f.AppearanceSourceType)
        featOk = (srcNow = CInt(AppearanceSourceTypeEnum.kOverrideAppearance))
        If Not featOk Then AddErr(errs, "피처 색 확인", "색이 들어가지 않음 (AppearanceSourceType=" & srcNow & ")", pd)
    Catch ex As Exception
        featOk = False
        AddErr(errs, "피처 색 적용", ex.Message, pd)
    End Try

    If Not featOk Then
        Dim n As Integer = PaintFaces(pd, faceList, a, failCount, errs)
        If n > 0 Then faceMarked = True
        Return n
    End If

    If covered.Count > 0 Then
        If PaintFaces(pd, covered, a, failCount, errs) > 0 Then faceMarked = True
    End If

    Return nFace

End Function


Function PaintFaces(pd As PartDocument, faceList As Object, a As Asset, _
                    ByRef failCount As Integer, errs As List(Of String)) As Integer

    If faceList Is Nothing Then Return 0

    Dim n As Integer = 0

    For Each o As Object In faceList

        Dim fc As Face = TryCast(o, Face)
        If fc Is Nothing Then Continue For

        If a Is Nothing Then
            failCount += 1
            Continue For
        End If

        Try
            SaveOriginal(fc, "HFC_FACE")
            fc.Appearance = a
            n += 1
        Catch ex As Exception
            failCount += 1
            AddErr(errs, "면 색 적용", ex.Message, pd)
        End Try
    Next

    Return n

End Function


Sub SaveOriginal(obj As Object, setName As String)

    If obj.AttributeSets.NameIsUsed(setName) Then Return

    Dim srcVal As Integer = CInt(obj.AppearanceSourceType)
    Dim aName As String = "-"

    If srcVal = CInt(AppearanceSourceTypeEnum.kOverrideAppearance) Then
        Try
            aName = CStr(obj.Appearance.Name)
        Catch
            aName = "-"
        End Try
    End If

    Dim st As AttributeSet = obj.AttributeSets.Add(setName)
    st.Add("src", ValueTypeEnum.kIntegerType, srcVal)
    st.Add("asset", ValueTypeEnum.kStringType, aName)

End Sub


Sub RestoreOriginal(pd As PartDocument, obj As Object, setName As String)

    Dim st As AttributeSet = obj.AttributeSets.Item(setName)
    Dim srcVal As Integer = CInt(st.Item("src").Value)
    Dim aName As String = CStr(st.Item("asset").Value)
    Dim done As Boolean = False
    Dim lastErr As String = ""

    If srcVal = CInt(AppearanceSourceTypeEnum.kOverrideAppearance) Then
        Dim a As Asset = FindAsset(pd, aName)
        If a IsNot Nothing AndAlso Not IsMyAsset(a, -1) Then
            Try
                obj.Appearance = a
                done = True
            Catch ex As Exception
                lastErr = ex.Message
            End Try
        End If
    Else
        done = TrySource(obj, CType(srcVal, AppearanceSourceTypeEnum), lastErr)
    End If

    If Not done Then done = ClearObjOverride(obj, lastErr)

    If Not done Then
        Throw New Exception("원래 색 설정을 넣지 못함 (원래 값=" & srcVal & ") " & lastErr)
    End If

    st.Delete()

End Sub


Function TrySource(obj As Object, v As AppearanceSourceTypeEnum, ByRef lastErr As String) As Boolean
    Try
        obj.AppearanceSourceType = v
    Catch ex As Exception
        lastErr = ex.Message
        Return False
    End Try
    Try
        Return CInt(obj.AppearanceSourceType) <> CInt(AppearanceSourceTypeEnum.kOverrideAppearance)
    Catch
        Return True
    End Try
End Function


Function ClearObjOverride(obj As Object, ByRef lastErr As String) As Boolean

    If TrySource(obj, AppearanceSourceTypeEnum.kPartAppearance, lastErr) Then Return True

    Try
        For Each v As AppearanceSourceTypeEnum In [Enum].GetValues(GetType(AppearanceSourceTypeEnum))
            Dim vn As String = v.ToString()
            If vn.Contains("Override") OrElse vn.Contains("Default") Then Continue For
            If v = AppearanceSourceTypeEnum.kPartAppearance Then Continue For
            If TrySource(obj, v, lastErr) Then Return True
        Next
    Catch
    End Try

    Return False

End Function


Sub RestorePart(pd As PartDocument, ByRef nItems As Integer, ByRef nFail As Integer, _
                errs As List(Of String))

    Dim failBefore As Integer = nFail

    Try
        For Each o As Object In pd.ComponentDefinition.Features
            Dim f As PartFeature = TryCast(o, PartFeature)
            If f Is Nothing Then Continue For
            Try
                If f.AttributeSets.NameIsUsed("HFC_FEAT") Then
                    RestoreOriginal(pd, f, "HFC_FEAT")
                    nItems += 1
                End If
            Catch ex As Exception
                nFail += 1
                AddErr(errs, "피처 되돌리기 (" & TypeLabel(f) & ")", ex.Message, pd)
            End Try
        Next
    Catch
    End Try

    If NeedFaceSearch(pd) Then

        Dim objs As ObjectCollection = Nothing
        Try
            objs = pd.AttributeManager.FindObjects("HFC_FACE")
        Catch
            objs = Nothing
        End Try

        If objs IsNot Nothing Then
            For Each o As Object In objs
                Dim fc As Face = TryCast(o, Face)
                If fc Is Nothing Then Continue For
                Try
                    RestoreOriginal(pd, fc, "HFC_FACE")
                    nItems += 1
                Catch ex As Exception
                    nFail += 1
                    AddErr(errs, "면 되돌리기", ex.Message, pd)
                End Try
            Next
        End If

    End If


    If nFail = failBefore Then
        Try
            Dim st As AttributeSet = MarkDoc(pd, "HFC_DOC")
            If Not st.NameIsUsed("restored") Then st.Add("restored", ValueTypeEnum.kIntegerType, 1)
            If Not st.NameIsUsed("ver") Then st.Add("ver", ValueTypeEnum.kIntegerType, 2)
            If st.NameIsUsed("faces") Then st.Item("faces").Delete()
        Catch
        End Try
    End If

End Sub


Function TypeLabel(f As PartFeature) As String
    If TypeOf f Is HoleFeature Then Return "구멍"
    If TypeOf f Is ThreadFeature Then Return "나사"
    If TypeOf f Is MirrorFeature Then Return "미러"
    If TypeOf f Is RectangularPatternFeature Then Return "직사각형 패턴"
    If TypeOf f Is CircularPatternFeature Then Return "원형 패턴"
    If TypeOf f Is SketchDrivenPatternFeature Then Return "스케치 패턴"
    Return "기타"
End Function


Sub FlagFaces(d As Inventor.Document)
    Try
        Dim st As AttributeSet = d.AttributeSets.Item("HFC_DOC")
        If Not st.NameIsUsed("faces") Then st.Add("faces", ValueTypeEnum.kIntegerType, 1)
    Catch
    End Try
End Sub


Function NeedFaceSearch(pd As PartDocument) As Boolean
    Try
        If Not pd.AttributeSets.NameIsUsed("HFC_DOC") Then Return True
        Dim st As AttributeSet = pd.AttributeSets.Item("HFC_DOC")
        If Not st.NameIsUsed("ver") Then Return True
        Return st.NameIsUsed("faces")
    Catch
        Return True
    End Try
End Function


Function HasPartMarks(pd As PartDocument) As Boolean
    Try
        If pd.AttributeSets.NameIsUsed("HFC_DOC") Then
            Return Not pd.AttributeSets.Item("HFC_DOC").NameIsUsed("restored")
        End If
    Catch
    End Try

    Try
        For Each a As Asset In pd.AppearanceAssets
            If IsMyAsset(a, -1) Then Return True
        Next
    Catch
    End Try

    Return False
End Function


Function GetAsset(pd As PartDocument, k As Integer, rgbs As Integer(,), _
                  forceNew As Boolean, errs As List(Of String)) As Asset

    Dim nm As String = "HFC_" & ClassKey(k)
    Dim disp As String = "가공색 - " & ClassLabel(k)
    Dim a As Asset = Nothing

    If Not forceNew Then
        a = FindMyAsset(pd, k)
        If a IsNot Nothing Then
            If SetAssetColor(a, k, rgbs, errs, pd) Then Return a
        End If
    End If

    For n As Integer = 1 To 20
        Dim tryName As String = nm
        Dim tryDisp As String = disp
        If n > 1 Then
            tryName = nm & "_" & n
            tryDisp = disp & " (" & n & ")"
        End If
        If AssetNameUsed(pd, tryName, tryDisp) Then Continue For

        Try
            a = pd.Assets.Add(AssetTypeEnum.kAssetTypeAppearance, "Generic", tryName, tryDisp)
        Catch ex As Exception
            a = Nothing
            AddErr(errs, "색 만들기", ex.Message & " [" & tryName & " / " & tryDisp & "]", pd)
        End Try

        If a IsNot Nothing AndAlso SetAssetColor(a, k, rgbs, errs, pd) Then Return a
    Next

    Return Nothing

End Function


Function IsMyAsset(a As Asset, k As Integer) As Boolean

    Dim an As String = ""
    Dim dn As String = ""
    Try
        an = a.Name
    Catch
    End Try
    Try
        dn = a.DisplayName
    Catch
    End Try

    If k < 0 Then
        Return an.StartsWith("HFC_", StringComparison.OrdinalIgnoreCase) OrElse _
               dn.StartsWith("가공색 - ")
    End If

    Dim nm As String = "HFC_" & ClassKey(k)
    Dim disp As String = "가공색 - " & ClassLabel(k)

    If String.Equals(an, nm, StringComparison.OrdinalIgnoreCase) Then Return True
    If an.StartsWith(nm & "_", StringComparison.OrdinalIgnoreCase) Then Return True
    If dn = disp Then Return True
    If dn.StartsWith(disp & " (") Then Return True
    Return False

End Function


Function FindMyAsset(pd As PartDocument, k As Integer) As Asset
    Try
        For Each a As Asset In pd.AppearanceAssets
            If IsMyAsset(a, k) Then Return a
        Next
    Catch
    End Try
    Return Nothing
End Function


Function AssetNameUsed(pd As PartDocument, nm As String, disp As String) As Boolean
    Try
        For Each a As Asset In pd.AppearanceAssets
            Dim an As String = ""
            Dim dn As String = ""
            Try
                an = a.Name
                dn = a.DisplayName
            Catch
            End Try
            If String.Equals(an, nm, StringComparison.OrdinalIgnoreCase) Then Return True
            If String.Equals(dn, disp, StringComparison.OrdinalIgnoreCase) Then Return True
        Next
    Catch
    End Try
    Return False
End Function


Function SetAssetColor(a As Asset, k As Integer, rgbs As Integer(,), _
                       errs As List(Of String), pd As PartDocument) As Boolean
    Try
        Dim cv As ColorAssetValue = CType(a.Item("generic_diffuse"), ColorAssetValue)
        cv.Value = ThisApplication.TransientObjects.CreateColor(rgbs(k, 0), rgbs(k, 1), rgbs(k, 2))
        Return True
    Catch ex As Exception
        AddErr(errs, "색 설정", ex.Message, pd)
        Return False
    End Try
End Function


Sub AddErr(errs As List(Of String), stage As String, msg As String, pd As PartDocument)
    If errs Is Nothing Then Return
    Dim head As String = stage & " : " & msg
    For Each e As String In errs
        If e.StartsWith(head) Then Return
    Next
    If errs.Count >= 20 Then Return
    errs.Add(head & "   (" & FileTitle(pd) & ")")
End Sub


Function FindAsset(pd As PartDocument, nm As String) As Asset

    If String.IsNullOrEmpty(nm) OrElse nm = "-" Then Return Nothing

    Try
        For Each a As Asset In pd.AppearanceAssets
            If String.Equals(a.Name, nm, StringComparison.OrdinalIgnoreCase) Then Return a
        Next
    Catch
    End Try

    Return Nothing

End Function


Function IsColorCovered(occ As ComponentOccurrence) As Boolean

    Dim cur As ComponentOccurrence = occ
    Dim guard As Integer = 0

    While cur IsNot Nothing AndAlso guard < 30
        Try
            If cur.AppearanceSourceType = AppearanceSourceTypeEnum.kOverrideAppearance Then Return True
        Catch
        End Try

        Try
            cur = cur.ParentOccurrence
        Catch
            cur = Nothing
        End Try
        guard += 1
    End While

    Return False

End Function


Function IsOverridden(occ As ComponentOccurrence) As Boolean
    Try
        Return occ.AppearanceSourceType = AppearanceSourceTypeEnum.kOverrideAppearance
    Catch
        Return False
    End Try
End Function


Sub ClearCoverChain(leaf As ComponentOccurrence, doneKeys As HashSet(Of String))

    Dim chain As New List(Of ComponentOccurrence)
    Dim cur As ComponentOccurrence = leaf
    Dim guard As Integer = 0

    While cur IsNot Nothing AndAlso guard < 30
        chain.Add(cur)
        Try
            cur = cur.ParentOccurrence
        Catch
            cur = Nothing
        End Try
        guard += 1
    End While

    For i As Integer = chain.Count - 1 To 0 Step -1
        Dim o As ComponentOccurrence = chain(i)
        Dim occId As String = OccKey(o)
        If doneKeys.Contains(occId) Then Continue For
        doneKeys.Add(occId)

        If IsOverridden(o) Then ClearOverride(o)
    Next

End Sub


Function ClearOverride(o As ComponentOccurrence) As Boolean

    Try
        o.AppearanceSourceType = AppearanceSourceTypeEnum.kPartAppearance
    Catch
    End Try
    If Not IsOverridden(o) Then Return True

    Try
        For Each v As AppearanceSourceTypeEnum In [Enum].GetValues(GetType(AppearanceSourceTypeEnum))
            Dim vn As String = v.ToString()
            If vn.Contains("Override") OrElse vn.Contains("Default") Then Continue For
            If v = AppearanceSourceTypeEnum.kPartAppearance Then Continue For

            Try
                o.AppearanceSourceType = v
            Catch
                Continue For
            End Try

            If Not IsOverridden(o) Then Return True
        Next
    Catch
    End Try

    Return False

End Function


Function OccKey(occ As ComponentOccurrence) As String

    Dim parts As New List(Of String)
    Dim cur As ComponentOccurrence = occ
    Dim guard As Integer = 0

    While cur IsNot Nothing AndAlso guard < 30
        Try
            parts.Insert(0, cur.Name)
            cur = cur.ParentOccurrence
        Catch
            cur = Nothing
        End Try
        guard += 1
    End While

    Return String.Join("\", parts.ToArray())

End Function


Function TempDvrName() As String
    Return "가공색상 확인(임시)"
End Function


Function ActivateTempDvr(asmDoc As AssemblyDocument) As Boolean

    Dim reps As DesignViewRepresentations = _
        asmDoc.ComponentDefinition.RepresentationsManager.DesignViewRepresentations

    If asmDoc.AttributeSets.NameIsUsed("HFC_ASM") Then
        Try
            Dim prevTemp As String = CStr(asmDoc.AttributeSets.Item("HFC_ASM").Item("tempDvr").Value)
            reps.Item(prevTemp).Activate()
            Return True
        Catch
            Return False
        End Try
    End If

    Dim orig As DesignViewRepresentation = Nothing
    Try
        orig = asmDoc.ComponentDefinition.RepresentationsManager.ActiveDesignViewRepresentation
    Catch
        Return False
    End Try
    If orig Is Nothing Then Return False

    Dim tmp As DesignViewRepresentation = Nothing
    Dim tName As String = ""

    DeleteTempDvrs(asmDoc, orig)

    For n As Integer = 1 To 9
        tName = TempDvrName()
        If n > 1 Then tName = TempDvrName() & " " & n
        If DvrExists(reps, tName) Then Continue For

        Try
            tmp = orig.Copy(tName)
        Catch
            tmp = Nothing
        End Try

        If tmp Is Nothing Then
            Try
                tmp = reps.Add(tName)
            Catch
                tmp = Nothing
            End Try
        End If

        If tmp IsNot Nothing Then Exit For
    Next

    If tmp Is Nothing Then Return False

    Try
        tmp.Locked = False
    Catch
    End Try

    Try
        tmp.Activate()
    Catch
        Try
            tmp.Delete()
        Catch
        End Try
        Return False
    End Try

    Dim st As AttributeSet = MarkDoc(asmDoc, "HFC_ASM")
    st.Add("origDvr", ValueTypeEnum.kStringType, orig.Name)
    st.Add("tempDvr", ValueTypeEnum.kStringType, tName)

    Return True

End Function


Function RestoreAsm(asmDoc As AssemblyDocument) As Boolean

    Dim st As AttributeSet = asmDoc.AttributeSets.Item("HFC_ASM")
    Dim origName As String = ""
    Dim tName As String = TempDvrName()

    Try
        origName = CStr(st.Item("origDvr").Value)
        tName = CStr(st.Item("tempDvr").Value)
    Catch
    End Try

    Dim reps As DesignViewRepresentations = _
        asmDoc.ComponentDefinition.RepresentationsManager.DesignViewRepresentations

    Try
        reps.Item(origName).Activate()
    Catch
        Return False
    End Try

    Try
        reps.Item(tName).Delete()
    Catch
    End Try

    Try
        DeleteTempDvrs(asmDoc, asmDoc.ComponentDefinition.RepresentationsManager.ActiveDesignViewRepresentation)
    Catch
    End Try

    Try
        st.Delete()
    Catch
    End Try

    Return True

End Function


Sub DeleteTempDvrs(asmDoc As AssemblyDocument, keep As DesignViewRepresentation)

    Dim reps As DesignViewRepresentations = _
        asmDoc.ComponentDefinition.RepresentationsManager.DesignViewRepresentations

    Dim olds As New List(Of DesignViewRepresentation)
    Try
        For Each r As DesignViewRepresentation In reps
            If r.Name.StartsWith(TempDvrName()) AndAlso r IsNot keep Then olds.Add(r)
        Next
    Catch
    End Try

    For Each r As DesignViewRepresentation In olds
        Try
            r.Delete()
        Catch
        End Try
    Next

End Sub


Function DvrExists(reps As DesignViewRepresentations, nm As String) As Boolean
    Try
        For Each r As DesignViewRepresentation In reps
            If String.Equals(r.Name, nm, StringComparison.OrdinalIgnoreCase) Then Return True
        Next
    Catch
    End Try
    Return False
End Function


Function MarkDoc(d As Inventor.Document, setName As String) As AttributeSet

    If d.AttributeSets.NameIsUsed(setName) Then
        Dim old As AttributeSet = d.AttributeSets.Item(setName)
        If old.NameIsUsed("restored") Then
            old.Delete()
        Else
            Return old
        End If
    End If

    Dim st As AttributeSet = d.AttributeSets.Add(setName)
    st.Add("session", ValueTypeEnum.kStringType, SessionId())
    st.Add("time", ValueTypeEnum.kStringType, DateTime.UtcNow.Ticks.ToString())
    st.Add("ver", ValueTypeEnum.kIntegerType, 2)
    Return st

End Function


Function PaintedThisSession(d As Inventor.Document, setName As String) As Boolean

    Try
        If Not d.AttributeSets.NameIsUsed(setName) Then Return False

        Dim st As AttributeSet = d.AttributeSets.Item(setName)
        If CStr(st.Item("session").Value) <> SessionId() Then Return False

        Dim marked As Long = CLng(CStr(st.Item("time").Value))
        Dim fp As String = DocPath(d)
        If fp = "" OrElse Not System.IO.File.Exists(fp) Then Return True

        Return System.IO.File.GetLastWriteTimeUtc(fp).Ticks < marked
    Catch
        Return False
    End Try

End Function


Function SessionId() As String
    Try
        Dim p As System.Diagnostics.Process = System.Diagnostics.Process.GetCurrentProcess()
        Return p.Id.ToString() & "_" & p.StartTime.ToUniversalTime().Ticks.ToString()
    Catch
        Return "?"
    End Try
End Function


Function IsMachinedNo(s As String, prefixes As List(Of String), maxRev As Integer, _
                      suffixes As List(Of String)) As Boolean

    If String.IsNullOrWhiteSpace(s) Then Return False

    Dim t As String = s.Trim().ToUpperInvariant()

    For Each sf As String In suffixes
        Dim su As String = sf.ToUpperInvariant()
        If su <> "" AndAlso t.Length > su.Length AndAlso t.EndsWith(su) Then
            t = t.Substring(0, t.Length - su.Length)
            Exit For
        End If
    Next

    If prefixes.Count > 0 Then
        Dim okPre As Boolean = False
        For Each p As String In prefixes
            If t.StartsWith(p.ToUpperInvariant()) Then
                okPre = True
                Exit For
            End If
        Next
        If Not okPre Then Return False
    End If

    Dim dash As Integer = t.LastIndexOf("-"c)
    If dash < 0 OrElse dash = t.Length - 1 Then Return False

    Dim tail As String = t.Substring(dash + 1)

    Dim i As Integer = 0
    While i < tail.Length AndAlso tail.Chars(i) >= "0"c AndAlso tail.Chars(i) <= "9"c
        i += 1
    End While
    If i = 0 Then Return False

    Dim rev As String = tail.Substring(i)
    If rev.Length > maxRev Then Return False

    For Each ch As Char In rev
        If ch < "A"c OrElse ch > "Z"c Then Return False
    Next

    Return True

End Function


Function SplitPrefixes(s As String) As List(Of String)
    Dim lst As New List(Of String)
    If String.IsNullOrWhiteSpace(s) Then Return lst
    For Each p As String In s.Split(","c)
        If p.Trim() <> "" Then lst.Add(p.Trim())
    Next
    Return lst
End Function


Function RuleText(prefixes As List(Of String), maxRev As Integer, suffixes As List(Of String)) As String
    Dim pre As String = "(접두어 안 봄)"
    If prefixes.Count > 0 Then pre = String.Join(" 또는 ", prefixes.ToArray()) & " 로 시작"
    Dim txt As String = pre & " + 끝이 -숫자 (리비전 문자 " & maxRev & "개까지)"
    If suffixes.Count > 0 Then txt &= " + 꼬리 " & String.Join(", ", suffixes.ToArray()) & " 허용"
    Return txt
End Function


Function ClassLabel(k As Integer) As String
    Select Case k
        Case 0 : Return "홀(드릴)"
        Case 1 : Return "카운터보어"
        Case 2 : Return "카운터싱크"
        Case 3 : Return "스폿페이스"
        Case 4 : Return "탭"
        Case 5 : Return "나사산"
    End Select
    Return "?"
End Function


Function ClassKey(k As Integer) As String
    Select Case k
        Case 0 : Return "DRILL"
        Case 1 : Return "CBORE"
        Case 2 : Return "CSINK"
        Case 3 : Return "SPOTFACE"
        Case 4 : Return "TAP"
        Case 5 : Return "THREAD"
    End Select
    Return "ETC"
End Function


Sub SetColor(rgbs As Integer(,), cNames As String(), k As Integer, spec As String)

    Dim nm As String = ClassLabel(k)
    Dim nums As String = spec

    Dim colon As Integer = spec.IndexOf(":"c)
    If colon >= 0 Then
        nm = spec.Substring(0, colon).Trim()
        nums = spec.Substring(colon + 1)
    End If

    Dim r As Integer = 128
    Dim g As Integer = 128
    Dim b As Integer = 128

    Try
        Dim parts As String() = nums.Split(","c)
        r = Clamp255(CInt(parts(0).Trim()))
        g = Clamp255(CInt(parts(1).Trim()))
        b = Clamp255(CInt(parts(2).Trim()))
    Catch
        r = 128 : g = 128 : b = 128
        nm &= "(설정 오류-회색)"
    End Try

    rgbs(k, 0) = r
    rgbs(k, 1) = g
    rgbs(k, 2) = b
    cNames(k) = nm

End Sub


Function Clamp255(v As Integer) As Integer
    If v < 0 Then Return 0
    If v > 255 Then Return 255
    Return v
End Function


Function ReadPN(d As Inventor.Document) As String
    Try
        Return CStr(d.PropertySets.Item("Design Tracking Properties").Item("Part Number").Value)
    Catch
        Return ""
    End Try
End Function


Function DocPath(d As Inventor.Document) As String
    Try
        Return d.FullFileName
    Catch
        Return ""
    End Try
End Function


Function FileTitle(d As Inventor.Document) As String
    Try
        Return System.IO.Path.GetFileNameWithoutExtension(DocPath(d))
    Catch
        Return ""
    End Try
End Function


Function DocLabel(d As Inventor.Document) As String
    Dim fn As String = FileTitle(d)
    Dim pn As String = ReadPN(d)
    If pn <> "" AndAlso Not String.Equals(pn, fn, StringComparison.OrdinalIgnoreCase) Then
        Return fn & "   [" & pn & "]"
    End If
    Return fn
End Function


Function IsContentPart(pd As PartDocument) As Boolean
    Try
        Return pd.ComponentDefinition.IsContentMember
    Catch
        Return False
    End Try
End Function


Function IsDirtyDoc(d As Inventor.Document) As Boolean
    Try
        Return d.Dirty
    Catch
        Return False
    End Try
End Function


Function SnapshotDocs() As List(Of Inventor.Document)
    Dim lst As New List(Of Inventor.Document)
    Try
        For Each d As Inventor.Document In ThisApplication.Documents
            lst.Add(d)
        Next
    Catch
    End Try
    Return lst
End Function


Function ListLines(items As List(Of String), maxLines As Integer) As String
    If items.Count = 0 Then Return "   (없음)" & vbCrLf
    Dim s As String = ""
    Dim n As Integer = Math.Min(items.Count, maxLines)
    For i As Integer = 0 To n - 1
        s &= "   · " & items(i) & vbCrLf
    Next
    If items.Count > n Then s &= "   ... 외 " & (items.Count - n) & "개" & vbCrLf
    Return s
End Function


Function MakeProgress(steps As Integer, title As String) As Inventor.ProgressBar
    Try
        Return ThisApplication.CreateProgressBar(False, Math.Max(steps, 1), title)
    Catch
        Return Nothing
    End Try
End Function


Sub StepProgress(pb As Inventor.ProgressBar, msg As String)
    Try
        ThisApplication.StatusBarText = msg
    Catch
    End Try

    If pb Is Nothing Then Return
    Try
        pb.Message = msg
        pb.UpdateProgress()
    Catch
    End Try
End Sub


Sub CloseProgress(pb As Inventor.ProgressBar)
    Try
        ThisApplication.StatusBarText = ""
    Catch
    End Try

    If pb Is Nothing Then Return
    Try
        pb.Close()
    Catch
    End Try
End Sub


Function ElapsedText(sw As System.Diagnostics.Stopwatch) As String
    Dim sec As Integer = CInt(Math.Round(sw.Elapsed.TotalSeconds))
    If sec < 60 Then Return sec & "초"
    Return (sec \ 60) & "분 " & (sec Mod 60) & "초"
End Function
