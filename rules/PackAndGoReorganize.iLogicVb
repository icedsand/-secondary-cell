' ============================================================================
'  Inventor iLogic Rule : Pack and Go 폴더 정리(made by pjh)
'  1) 미리보기  2) 복사  3) 재연결 (새 ipj 활성화 + 빈 부품 하나 열고 실행)
' ============================================================================

Sub Main()

    ' ── 설정 ──
    ' 원본 (Vault 작업 폴더)
    Dim SRC_ROOT As String = "O:\JASTECH1\JASTECH1\B5. 개발설계TF 폴더 (아산)\01. GM SAMPLE STACKING 검토"
    ' 라이브러리
    Dim LIB_ROOT As String = "O:\JASTECH1\JASTECH1\04. Library"
    ' 결과 위치 기본값 (실행 때 고르는 창이 뜸)
    Dim DST_BASE As String = "O:\스태킹 PAG"

    ' 원래 구조 그대로 옮길 폴더 / 공용부품 폴더 / 공용부품 이름 / 구매품 폴더 이름 / 타프로젝트 폴더 / 제외 폴더
    Dim ASIS_FOLDERS    As String = "99. 자재"
    Dim COMMON_LIB_DIRS As String = "Z. BOLT|Z. NUT|Z. WASHER"
    Dim COMMON_KEYWORDS As String = "와셔|WASHER"
    Dim PURCH_DIR_KEYS  As String = "구매품|표준품"
    Dim OTHER_PROJ_DIR  As String = "99. 타프로젝트"
    Dim SKIP_DIRS       As String = "_V|OldVersions"

    Dim TTL As String = "Pack and Go 폴더 정리"

    Dim S As New Dictionary(Of String, Object)
    S("TTL") = TTL
    S("SRC") = NormDir(SRC_ROOT)
    S("LIB") = NormDir(LIB_ROOT)
    S("ROOTNAME") = System.IO.Path.GetFileName(CStr(S("SRC")))
    S("DST") = System.IO.Path.Combine(NormDir(DST_BASE), CStr(S("ROOTNAME")))
    S("ASIS") = SplitList(ASIS_FOLDERS)
    S("COMDIRS") = SplitList(COMMON_LIB_DIRS)
    S("COMKEYS") = SplitList(COMMON_KEYWORDS)
    S("SKIPDIRS") = SplitList(SKIP_DIRS)
    S("PURCHKEYS") = SplitList(PURCH_DIR_KEYS)
    S("OTHERDIR") = OTHER_PROJ_DIR
    S("LOGDIR") = System.IO.Path.Combine(CStr(S("DST")), "_정리로그")

    Dim MODE_PREVIEW As String = "1. 미리보기  - 어디로 갈지 목록(CSV)만 만든다"
    Dim MODE_COPY    As String = "2. 복사      - 파일 복사 + 프로젝트 파일 생성"
    Dim MODE_RELINK  As String = "3. 재연결    - 새 프로젝트에서 참조를 새 위치로"

    Dim modes As New List(Of String)
    modes.Add(MODE_PREVIEW)
    modes.Add(MODE_COPY)
    modes.Add(MODE_RELINK)

    Dim sel = InputListBox("실행할 단계를 고르세요." & vbCrLf & vbCrLf & _
                           "원본 : " & CStr(S("SRC")) & vbCrLf & _
                           "결과 : 미리보기 / 복사는 다음 창에서 고릅니다." & vbCrLf & _
                           "       재연결은 활성화된 새 프로젝트 위치를 씁니다.", _
                           modes.ToArray(), MODE_PREVIEW, Title:=TTL, ListName:="단계")
    If sel Is Nothing OrElse CStr(sel) = "" Then Return
    Dim mode As String = CStr(sel)

    If mode = MODE_RELINK Then
        DoRelink(S)
        Return
    End If

    Dim isCopy As Boolean = (mode = MODE_COPY)

    Dim baseDir As String = ReadLastDst()
    If baseDir = "" OrElse Not System.IO.Directory.Exists(baseDir) Then baseDir = NormDir(DST_BASE)
    Dim picked As String = PickFolder(baseDir, _
        "결과를 만들 폴더를 고르세요." & vbCrLf & _
        "이 안에 """ & CStr(S("ROOTNAME")) & """ 폴더가 만들어집니다.")
    If picked = "" Then Return
    picked = NormDir(picked)
    If String.Equals(System.IO.Path.GetFileName(picked), CStr(S("ROOTNAME")), StringComparison.OrdinalIgnoreCase) Then
        S("DST") = picked
        SaveLastDst(System.IO.Path.GetDirectoryName(picked))
    Else
        S("DST") = System.IO.Path.Combine(picked, CStr(S("ROOTNAME")))
        SaveLastDst(picked)
    End If
    S("LOGDIR") = System.IO.Path.Combine(CStr(S("DST")), "_정리로그")

    If Not System.IO.Directory.Exists(CStr(S("SRC"))) Then
        MessageBox.Show("원본 폴더가 없습니다." & vbCrLf & CStr(S("SRC")) & vbCrLf & vbCrLf & _
                        "규칙 맨 위 설정의 SRC_ROOT 를 확인하세요.", TTL)
        Return
    End If
    If Not System.IO.Directory.Exists(CStr(S("LIB"))) Then
        MessageBox.Show("라이브러리 폴더가 없습니다." & vbCrLf & CStr(S("LIB")) & vbCrLf & vbCrLf & _
                        "규칙 맨 위 설정의 LIB_ROOT 를 확인하세요." & vbCrLf & _
                        "(인벤터 프로젝트 창에서 Vault 프로젝트의 라이브러리 경로)", TTL)
        Return
    End If

    Dim host As Inventor.Document = Nothing
    Try
        host = ThisApplication.ActiveDocument
    Catch
        host = Nothing
    End Try

    If host Is Nothing OrElse host.DocumentType <> Inventor.DocumentTypeEnum.kAssemblyDocumentObject Then
        MessageBox.Show("원본 전체 조립도(또는 유닛 조립도)를 열고 실행하세요.", TTL)
        Return
    End If

    Dim hostPath As String = host.FullFileName
    If Not IsUnder(hostPath, CStr(S("SRC"))) Then
        MessageBox.Show("열려 있는 조립도가 원본 폴더 안에 있지 않습니다." & vbCrLf & vbCrLf & _
                        "조립도 : " & hostPath & vbCrLf & _
                        "원본   : " & CStr(S("SRC")), TTL)
        Return
    End If

    Dim hostSegs() As String = RelSegs(hostPath, CStr(S("SRC")))
    Dim topMode As Boolean = (hostSegs.Length = 1)
    If Not topMode AndAlso InList(CfgList(S, "ASIS"), hostSegs(0)) Then
        MessageBox.Show(hostSegs(0) & " 폴더는 원래 구조 그대로 옮기는 폴더입니다." & vbCrLf & _
                        "전체 조립도나 유닛 조립도에서 실행하세요.", TTL)
        Return
    End If

    S("HOST") = hostPath
    S("TOPMODE") = topMode

    If IsUnder(CStr(S("DST")), CStr(S("SRC"))) OrElse IsUnder(CStr(S("SRC")), CStr(S("DST"))) Then
        MessageBox.Show("결과 위치와 원본 위치가 겹칩니다. 설정을 확인하세요.", TTL)
        Return
    End If

    InitPlanState(S)

    Try
        ThisApplication.StatusBarText = TTL & " : 조립 구조 읽는 중..."
        BuildGraph(S, host)

        ThisApplication.StatusBarText = TTL & " : 유닛 폴더 읽는 중..."
        Dim targets As New List(Of String)
        AnalyzeUnits(S)
        If topMode Then
            targets.AddRange(CType(S("units"), List(Of String)))
        Else
            targets.Add(hostSegs(0))
        End If
        S("targets") = targets

        ThisApplication.StatusBarText = TTL & " : 배치 계획 세우는 중..."
        MakePlan(S)
    Catch ex As Exception
        ThisApplication.StatusBarText = ""
        MessageBox.Show("계획을 세우다가 오류가 났습니다." & vbCrLf & vbCrLf & ex.Message, TTL)
        Return
    End Try
    ThisApplication.StatusBarText = ""

    Dim summary As String = PlanSummary(S)
    Dim csvPath As String = ""
    Try
        System.IO.Directory.CreateDirectory(CStr(S("LOGDIR")))
        csvPath = System.IO.Path.Combine(CStr(S("LOGDIR")), _
                  "미리보기_" & DateTime.Now.ToString("yyyyMMdd_HHmmss") & ".csv")
        WritePlanCsv(S, csvPath)
    Catch ex As Exception
        MessageBox.Show("미리보기 CSV 를 쓰지 못했습니다." & vbCrLf & ex.Message, TTL)
        csvPath = ""
    End Try

    If Not isCopy Then
        Dim msg As String = summary & vbCrLf & vbCrLf & _
                            "목록 : " & csvPath & vbCrLf & vbCrLf & _
                            "아무 파일도 복사하지 않았습니다." & vbCrLf & _
                            "CSV 를 지금 열까요?"
        If csvPath <> "" AndAlso MessageBox.Show(msg, TTL & " - 미리보기", MessageBoxButtons.YesNo) = DialogResult.Yes Then
            OpenWithShell(csvPath)
        End If
        Return
    End If

    Dim ask As String = summary & vbCrLf & vbCrLf & _
                        "목록 : " & csvPath & vbCrLf & vbCrLf & _
                        "결과 위치로 복사하고 프로젝트 파일을 만듭니다." & vbCrLf & _
                        "원본은 건드리지 않습니다. 이미 있는 파일은 건너뜁니다." & vbCrLf & vbCrLf & _
                        "진행할까요?"
    If MessageBox.Show(ask, TTL & " - 복사 확인", MessageBoxButtons.OKCancel) <> DialogResult.OK Then Return

    Dim report As String = ExecuteCopy(S)
    MessageBox.Show(report, TTL & " - 복사 완료")

End Sub

Function NormDir(p As String) As String
    If String.IsNullOrWhiteSpace(p) Then Return ""
    Dim r As String = p.Trim()
    Try
        r = System.IO.Path.GetFullPath(r)
    Catch
    End Try
    Return r.TrimEnd("\"c)
End Function

Function IsUnder(p As String, root As String) As Boolean
    If String.IsNullOrEmpty(p) OrElse String.IsNullOrEmpty(root) Then Return False
    Return p.StartsWith(root & "\", StringComparison.OrdinalIgnoreCase)
End Function

Function RelSegs(p As String, root As String) As String()
    Return p.Substring(root.Length + 1).Split("\"c)
End Function

Function SplitList(s As String) As List(Of String)
    Dim r As New List(Of String)
    For Each t As String In s.Split("|"c)
        If t.Trim() <> "" Then r.Add(t.Trim())
    Next
    Return r
End Function

Function CfgList(S As Dictionary(Of String, Object), key As String) As List(Of String)
    Return CType(S(key), List(Of String))
End Function

Function InList(lst As List(Of String), v As String) As Boolean
    For Each t As String In lst
        If String.Equals(t, v, StringComparison.OrdinalIgnoreCase) Then Return True
    Next
    Return False
End Function

Function HasKeyword(S As Dictionary(Of String, Object), text As String) As Boolean
    For Each k As String In CfgList(S, "COMKEYS")
        If text.IndexOf(k, StringComparison.OrdinalIgnoreCase) >= 0 Then Return True
    Next
    Return False
End Function

Function Ext(p As String) As String
    Return System.IO.Path.GetExtension(p).ToLowerInvariant()
End Function

Function IsDrawingExt(p As String) As Boolean
    Dim fe As String = Ext(p)
    Return fe = ".idw" OrElse fe = ".dwg"
End Function

Function IsModelExt(p As String) As Boolean
    Dim fe As String = Ext(p)
    Return fe = ".ipt" OrElse fe = ".iam"
End Function

Function NewDict() As Dictionary(Of String, String)
    Return New Dictionary(Of String, String)(StringComparer.OrdinalIgnoreCase)
End Function

Function NewSet() As HashSet(Of String)
    Return New HashSet(Of String)(StringComparer.OrdinalIgnoreCase)
End Function

Function AddNote(note As String, more As String) As String
    If String.IsNullOrEmpty(note) Then Return more
    If note.Contains(more) Then Return note
    Return note & " / " & more
End Function

Function IsSkipped(S As Dictionary(Of String, Object), p As String) As Boolean
    Dim skipDirs As List(Of String) = CfgList(S, "SKIPDIRS")
    Dim segs() As String = p.Split("\"c)
    For i As Integer = 0 To segs.Length - 2
        If InList(skipDirs, segs(i)) Then Return True
    Next
    Dim nm As String = System.IO.Path.GetFileName(p)
    If nm.StartsWith("~$") Then Return True
    If String.Equals(nm, "Thumbs.db", StringComparison.OrdinalIgnoreCase) Then Return True
    If String.Equals(nm, "desktop.ini", StringComparison.OrdinalIgnoreCase) Then Return True
    Dim fe As String = Ext(p)
    If fe = ".ipj" OrElse fe = ".lck" OrElse fe = ".dwl" OrElse fe = ".dwl2" Then Return True
    Return False
End Function

Function EnumFiles(S As Dictionary(Of String, Object), dir As String) As List(Of String)
    Dim result As New List(Of String)
    Dim stack As New List(Of String)
    stack.Add(dir)
    Dim skipDirs As List(Of String) = CfgList(S, "SKIPDIRS")

    Do While stack.Count > 0
        Dim cur As String = stack(stack.Count - 1)
        stack.RemoveAt(stack.Count - 1)
        Try
            Dim files() As String = System.IO.Directory.GetFiles(cur)
            Array.Sort(files, StringComparer.OrdinalIgnoreCase)
            For Each f As String In files
                If Not IsSkipped(S, f) Then result.Add(f)
            Next
            Dim subs() As String = System.IO.Directory.GetDirectories(cur)
            Array.Sort(subs, StringComparer.OrdinalIgnoreCase)
            For i As Integer = subs.Length - 1 To 0 Step -1
                If Not InList(skipDirs, System.IO.Path.GetFileName(subs(i))) Then stack.Add(subs(i))
            Next
        Catch
        End Try
    Loop
    Return result
End Function

Function ParseCode(fileName As String) As String()
    Dim baseName As String = System.IO.Path.GetFileNameWithoutExtension(fileName)
    Dim segs() As String = baseName.Split("-"c)

    For i As Integer = 1 To segs.Length - 1
        Dim core As String = segs(i)
        Dim cut As Integer = core.IndexOf("("c)
        If cut >= 0 Then core = core.Substring(0, cut)
        core = core.Trim().ToUpperInvariant()

        Dim k As Integer = 0
        Do While k < core.Length AndAlso core(k) >= "A"c AndAlso core(k) <= "Z"c
            k += 1
        Loop
        If k < 2 OrElse k > 6 Then Continue For
        If core.Length < k + 2 Then Continue For
        If core(k) < "0"c OrElse core(k) > "9"c Then Continue For
        If core(k + 1) < "0"c OrElse core(k + 1) > "9"c Then Continue For

        Dim tail As String = core.Substring(k + 2)
        If tail.Length > 2 Then Continue For
        Dim ok As Boolean = True
        For Each c As Char In tail
            If c < "A"c OrElse c > "Z"c Then
                ok = False
                Exit For
            End If
        Next
        If Not ok Then Continue For

        Dim part As String = ""
        If i < segs.Length - 1 Then part = String.Join("-", segs, i + 1, segs.Length - i - 1)
        Return New String() {core.Substring(0, k), core.Substring(k, 2), part}
    Next

    Return Nothing
End Function

Function PurchInfo(S As Dictionary(Of String, Object), p As String) As String()
    Dim libRoot As String = CStr(S("LIB"))
    Dim srcRoot As String = CStr(S("SRC"))
    Dim fileName As String = System.IO.Path.GetFileName(p)

    If IsUnder(p, libRoot) Then
        Dim segs() As String = RelSegs(p, libRoot)

        Dim common As Boolean = False
        If segs.Length >= 2 AndAlso InList(CfgList(S, "COMDIRS"), segs(0)) Then common = True
        For i As Integer = 0 To Math.Min(2, segs.Length - 1) - 1
            If HasKeyword(S, segs(i)) Then common = True
        Next
        If segs.Length < 4 AndAlso HasKeyword(S, fileName) Then common = True

        If common Then Return New String() {"", "공용부품\" & fileName}
        If segs.Length >= 4 Then
            Dim pkg As String = System.IO.Path.Combine(libRoot, segs(0), segs(1), segs(2))
            Return New String() {pkg, String.Join("\", segs, 2, segs.Length - 2)}
        End If
        Return New String() {"", fileName}
    End If

    If IsUnder(p, srcRoot) Then
        Dim segs() As String = RelSegs(p, srcRoot)
        For k As Integer = 1 To segs.Length - 2
            If DirKind(S, segs(k)) = "PURCH" Then
                Dim baseDir As String = System.IO.Path.Combine(srcRoot, String.Join("\", segs, 0, k + 1))
                Dim rest As Integer = segs.Length - (k + 1)
                If rest = 1 Then
                    If HasKeyword(S, fileName) Then Return New String() {"", "공용부품\" & fileName}
                    Return New String() {"", fileName}
                End If
                Dim first As String = segs(k + 1)
                If first = "공용부품" Then
                    Return New String() {"", String.Join("\", segs, k + 1, rest)}
                End If
                Return New String() {System.IO.Path.Combine(baseDir, first), String.Join("\", segs, k + 1, rest)}
            End If
        Next
        Return Nothing
    End If

    If Ext(p) = ".ipt" OrElse Ext(p) = ".iam" Then
        If Not IsMachined(S, p) Then
            If HasKeyword(S, fileName) Then Return New String() {"", "공용부품\" & fileName}
            Return New String() {"", fileName}
        End If
    End If

    Return Nothing
End Function

Function ProjectOf(fileName As String) As String
    Dim segs() As String = System.IO.Path.GetFileNameWithoutExtension(fileName).Split("-"c)
    If segs.Length < 3 Then Return ""

    Dim s0 As String = segs(0).Trim().ToUpperInvariant()
    If s0.Length < 2 OrElse s0.Length > 6 Then Return ""
    For Each c As Char In s0
        If c < "A"c OrElse c > "Z"c Then Return ""
    Next

    Dim s1 As String = segs(1).Trim().ToUpperInvariant()
    Dim k As Integer = 0
    Do While k < s1.Length AndAlso s1(k) >= "A"c AndAlso s1(k) <= "Z"c
        k += 1
    Loop
    Dim nd As Integer = s1.Length - k
    If k < 1 OrElse k > 4 OrElse nd < 2 OrElse nd > 6 Then Return ""
    For i As Integer = k To s1.Length - 1
        If s1(i) < "0"c OrElse s1(i) > "9"c Then Return ""
    Next

    Dim p() As String = ParseCode("x-" & segs(2) & ".ipt")
    If p Is Nothing Then Return ""
    Return s0 & "-" & s1
End Function

Function IsMachined(S As Dictionary(Of String, Object), p As String) As Boolean
    If ProjectOf(p) <> "" Then Return True
    If Ext(p) <> ".iam" Then Return False
    Dim memo As Dictionary(Of String, String) = GetDict(S, "machMemo")
    If memo.ContainsKey(p) Then Return memo(p) = "1"
    memo(p) = "0"
    Dim r As Boolean = False
    For Each c As String In ChildrenOf(S, p)
        If IsUnder(c, CStr(S("LIB"))) Then Continue For
        If IsMachined(S, c) Then
            r = True
            Exit For
        End If
    Next
    memo(p) = If(r, "1", "0")
    Return r
End Function

Function IsOutside(S As Dictionary(Of String, Object), p As String) As Boolean
    Return Not IsUnder(p, CStr(S("SRC"))) AndAlso Not IsUnder(p, CStr(S("LIB")))
End Function

Function OpenWithShell(p As String) As Boolean
    Try
        Dim psi As New System.Diagnostics.ProcessStartInfo(p)
        psi.UseShellExecute = True
        System.Diagnostics.Process.Start(psi)
        Return True
    Catch
        Return False
    End Try
End Function

Function CsvField(s As String) As String
    If s Is Nothing Then s = ""
    Return """" & s.Replace("""", """""") & """"
End Function

Function CopyFileSafe(src As String, dst As String) As String
    Try
        If System.IO.File.Exists(dst) Then Return "exists"
        System.IO.Directory.CreateDirectory(System.IO.Path.GetDirectoryName(dst))
        System.IO.File.Copy(src, dst, False)
        Dim attr As System.IO.FileAttributes = System.IO.File.GetAttributes(dst)
        If (attr And System.IO.FileAttributes.ReadOnly) = System.IO.FileAttributes.ReadOnly Then
            System.IO.File.SetAttributes(dst, attr And Not System.IO.FileAttributes.ReadOnly)
        End If
        Return "copied"
    Catch ex As Exception
        Return ex.Message
    End Try
End Function

Sub InitPlanState(S As Dictionary(Of String, Object))
    S("graph") = New List(Of String)
    S("graphSet") = NewSet()
    S("children") = New Dictionary(Of String, List(Of String))(StringComparer.OrdinalIgnoreCase)
    S("parents") = New Dictionary(Of String, List(Of String))(StringComparer.OrdinalIgnoreCase)
    S("hasRefs") = NewSet()
    S("missing") = New List(Of String)

    S("units") = New List(Of String)
    S("unitCode") = NewDict()
    S("unitFiles") = New Dictionary(Of String, List(Of String))(StringComparer.OrdinalIgnoreCase)
    S("unitSubs") = New Dictionary(Of String, List(Of String))(StringComparer.OrdinalIgnoreCase)
    S("tempSubNames") = New List(Of String)
    S("usedBy") = NewDict()
    S("moveSub") = NewDict()
    S("extParent") = NewDict()
    S("destMemo") = NewDict()
    S("machMemo") = NewDict()
    S("otherGroups") = New List(Of String)

    S("plan") = New List(Of String())
    S("dstOwner") = NewDict()
    S("primary") = NewDict()
    S("purchKey") = NewDict()
    S("purchPlaced") = NewSet()
    S("pkgDone") = NewSet()
    S("pkgDirOwner") = NewDict()
    S("ctxMemo") = NewDict()
    S("warn") = NewDict()
    S("excluded") = New List(Of String())
End Sub

Function GetList(S As Dictionary(Of String, Object), key As String) As List(Of String)
    Return CType(S(key), List(Of String))
End Function

Function GetDict(S As Dictionary(Of String, Object), key As String) As Dictionary(Of String, String)
    Return CType(S(key), Dictionary(Of String, String))
End Function

Function GetSet(S As Dictionary(Of String, Object), key As String) As HashSet(Of String)
    Return CType(S(key), HashSet(Of String))
End Function

Function GetDL(S As Dictionary(Of String, Object), key As String) As Dictionary(Of String, List(Of String))
    Return CType(S(key), Dictionary(Of String, List(Of String)))
End Function

Function Plan(S As Dictionary(Of String, Object)) As List(Of String())
    Return CType(S("plan"), List(Of String()))
End Function

Sub Warn(S As Dictionary(Of String, Object), f As String, msg As String)
    Dim w As Dictionary(Of String, String) = GetDict(S, "warn")
    If w.ContainsKey(f) Then
        w(f) = AddNote(w(f), msg)
    Else
        w(f) = msg
    End If
End Sub

Function WarnOf(S As Dictionary(Of String, Object), f As String) As String
    Dim w As Dictionary(Of String, String) = GetDict(S, "warn")
    If w.ContainsKey(f) Then Return w(f)
    Return ""
End Function

Function ChildrenOf(S As Dictionary(Of String, Object), f As String) As List(Of String)
    Dim c As Dictionary(Of String, List(Of String)) = GetDL(S, "children")
    If c.ContainsKey(f) Then Return c(f)
    Return New List(Of String)
End Function

Function ParentsOf(S As Dictionary(Of String, Object), f As String) As List(Of String)
    Dim c As Dictionary(Of String, List(Of String)) = GetDL(S, "parents")
    If c.ContainsKey(f) Then Return c(f)
    Return New List(Of String)
End Function

Sub BuildGraph(S As Dictionary(Of String, Object), host As Inventor.Document)
    Dim graph As List(Of String) = GetList(S, "graph")
    Dim graphSet As HashSet(Of String) = GetSet(S, "graphSet")
    Dim children As Dictionary(Of String, List(Of String)) = GetDL(S, "children")
    Dim parents As Dictionary(Of String, List(Of String)) = GetDL(S, "parents")
    Dim hasRefs As HashSet(Of String) = GetSet(S, "hasRefs")
    Dim missing As List(Of String) = GetList(S, "missing")

    Dim files As New List(Of Inventor.File)
    files.Add(host.File)
    For Each f As Inventor.File In host.File.AllReferencedFiles
        files.Add(f)
    Next

    For Each f As Inventor.File In files
        Dim fp As String = ""
        Try
            fp = f.FullFileName
        Catch
            Continue For
        End Try
        If graphSet.Contains(fp) Then Continue For
        graphSet.Add(fp)
        graph.Add(fp)

        Dim kids As New List(Of String)
        children(fp) = kids

        Dim fds As New List(Of Inventor.FileDescriptor)
        Try
            For Each fd As Inventor.FileDescriptor In f.ReferencedFileDescriptors
                fds.Add(fd)
            Next
        Catch
        End Try
        If fds.Count > 0 Then hasRefs.Add(fp)

        For Each fd As Inventor.FileDescriptor In fds
            Try
                If fd.ReferenceMissing Then
                    missing.Add(fp & "|" & fd.FullFileName)
                    Continue For
                End If
                Dim cp As String = fd.ReferencedFile.FullFileName
                If Not kids.Contains(cp) Then kids.Add(cp)
                If Not parents.ContainsKey(cp) Then parents(cp) = New List(Of String)
                If Not parents(cp).Contains(fp) Then parents(cp).Add(fp)
            Catch
            End Try
        Next
    Next
End Sub

Sub AnalyzeUnits(S As Dictionary(Of String, Object))
    Dim srcRoot As String = CStr(S("SRC"))
    Dim units As List(Of String) = GetList(S, "units")
    Dim unitCode As Dictionary(Of String, String) = GetDict(S, "unitCode")
    Dim unitFiles As Dictionary(Of String, List(Of String)) = GetDL(S, "unitFiles")
    Dim unitSubs As Dictionary(Of String, List(Of String)) = GetDL(S, "unitSubs")
    Dim moveSub As Dictionary(Of String, String) = GetDict(S, "moveSub")

    Dim dirs() As String = System.IO.Directory.GetDirectories(srcRoot)
    Array.Sort(dirs, StringComparer.OrdinalIgnoreCase)

    For Each ud As String In dirs
        Dim u As String = System.IO.Path.GetFileName(ud)
        If InList(CfgList(S, "ASIS"), u) Then Continue For
        If InList(CfgList(S, "SKIPDIRS"), u) Then Continue For
        units.Add(u)

        Dim files As List(Of String) = EnumFiles(S, ud)
        unitFiles(u) = files

        Dim subs As New List(Of String)
        Dim subByNum As Dictionary(Of String, String) = NewDict()
        Dim lvl1() As String = New String() {}
        Try
            lvl1 = System.IO.Directory.GetDirectories(ud)
        Catch
        End Try
        Array.Sort(lvl1, StringComparer.OrdinalIgnoreCase)
        For Each sd As String In lvl1
            Dim nm As String = System.IO.Path.GetFileName(sd)
            If InList(CfgList(S, "SKIPDIRS"), nm) Then Continue For
            If DirKind(S, nm) = "SUBS" Then
                Dim lvl2() As String = New String() {}
                Try
                    lvl2 = System.IO.Directory.GetDirectories(sd)
                Catch
                End Try
                Array.Sort(lvl2, StringComparer.OrdinalIgnoreCase)
                For Each sd2 As String In lvl2
                    Dim nm2 As String = System.IO.Path.GetFileName(sd2)
                    If InList(CfgList(S, "SKIPDIRS"), nm2) OrElse subs.Contains(nm2) Then Continue For
                    subs.Add(nm2)
                Next
            ElseIf IsSubUnitDir(S, nm) Then
                If Not subs.Contains(nm) Then subs.Add(nm)
            End If
        Next
        For Each sn As String In subs
            Dim num As String = LeadingNumber(sn)
            If num <> "" AndAlso Not subByNum.ContainsKey(num) Then subByNum(num) = sn
        Next

        Dim counts As New Dictionary(Of String, Integer)(StringComparer.OrdinalIgnoreCase)
        Dim preferred As String = ""
        For Each f As String In files
            If Not IsModelExt(f) Then Continue For
            If PurchInfo(S, f) IsNot Nothing Then Continue For
            Dim p() As String = ParseCode(f)
            If p Is Nothing Then Continue For
            If counts.ContainsKey(p(0)) Then
                counts(p(0)) += 1
            Else
                counts(p(0)) = 1
            End If
            If preferred = "" AndAlso Ext(f) = ".iam" AndAlso p(1) = "00" AndAlso p(2) = "" Then preferred = p(0)
        Next
        Dim code As String = preferred
        If code = "" Then
            Dim best As Integer = 0
            For Each kv As KeyValuePair(Of String, Integer) In counts
                If kv.Value > best Then
                    best = kv.Value
                    code = kv.Key
                End If
            Next
        End If
        unitCode(u) = code

        Dim level As String = UnitLevel(S, u, ud, code, files)

        If code <> "" Then
            For Each f As String In files
                If PurchInfo(S, f) IsNot Nothing Then Continue For
                Dim e2 As String = Ext(f)
                If e2 <> ".iam" AndAlso e2 <> ".idw" AndAlso e2 <> ".dwg" Then Continue For
                Dim segs() As String = RelSegs(f, srcRoot)
                If segs.Length <> 3 OrElse DirKind(S, segs(1)) <> "ASM" Then Continue For
                Dim p() As String = ParseCode(f)
                If p Is Nothing Then Continue For
                If Not String.Equals(p(0), code, StringComparison.OrdinalIgnoreCase) Then Continue For
                If p(1) = "00" OrElse p(1) = level Then Continue For
                If Not subByNum.ContainsKey(p(1)) Then
                    Dim tmp As String = p(1) & ". " & code & p(1)
                    subByNum(p(1)) = tmp
                    subs.Add(tmp)
                    GetList(S, "tempSubNames").Add(u & " \ " & tmp)
                End If
                moveSub(f) = subByNum(p(1))
            Next
        End If

        subs.Sort(StringComparer.OrdinalIgnoreCase)
        unitSubs(u) = subs
    Next
End Sub

Function UnitLevel(S As Dictionary(Of String, Object), u As String, ud As String, code As String, files As List(Of String)) As String
    If code = "" Then Return "00"
    Dim nums As New List(Of String)
    For Each f As String In files
        If PurchInfo(S, f) IsNot Nothing Then Continue For
        Dim p() As String = ParseCode(f)
        If p Is Nothing Then Continue For
        If Not String.Equals(p(0), code, StringComparison.OrdinalIgnoreCase) Then Continue For
        If Not nums.Contains(p(1)) Then nums.Add(p(1))
    Next
    If nums.Contains("00") Then Return "00"

    Dim unitAsms As New List(Of String)
    If CBool(S("TOPMODE")) Then
        unitAsms.AddRange(ChildrenOf(S, CStr(S("HOST"))))
    Else
        unitAsms.Add(CStr(S("HOST")))
    End If
    For Each ua As String In unitAsms
        If Ext(ua) <> ".iam" OrElse Not IsUnder(ua, ud) Then Continue For
        Dim p() As String = ParseCode(ua)
        If p Is Nothing OrElse p(2) <> "" Then Continue For
        If String.Equals(p(0), code, StringComparison.OrdinalIgnoreCase) Then Return p(1)
    Next
    If nums.Count = 1 Then Return nums(0)
    Return "00"
End Function

Function DirKind(S As Dictionary(Of String, Object), nm As String) As String
    If nm.Contains("하부조립도") Then Return "SUBS"
    For Each k As String In CfgList(S, "PURCHKEYS")
        If nm.Contains(k) Then Return "PURCH"
    Next
    If nm.Contains("조립도") Then Return "ASM"
    If nm.Contains("부품도") OrElse nm.Contains("가공품") Then Return "PART"
    Return ""
End Function

Function IsSubUnitDir(S As Dictionary(Of String, Object), nm As String) As Boolean
    Dim num As String = LeadingNumber(nm)
    If num = "" OrElse num = "00" Then Return False
    If DirKind(S, nm) <> "" Then Return False
    If nm.Contains("미분류") OrElse nm.Contains("자재") OrElse nm.Contains("공용부품") Then Return False
    Return True
End Function

Function LeadingNumber(nm As String) As String
    Dim k As Integer = 0
    Do While k < nm.Length AndAlso nm(k) >= "0"c AndAlso nm(k) <= "9"c
        k += 1
    Loop
    If k = 0 OrElse k > 2 Then Return ""
    If k < nm.Length Then
        Dim c As Char = nm(k)
        If c <> "."c AndAlso c <> " "c AndAlso c <> "_"c AndAlso c <> "-"c Then Return ""
    End If
    Return nm.Substring(0, k).PadLeft(2, "0"c)
End Function

Function UnitHasSub(S As Dictionary(Of String, Object), u As String) As Boolean
    Dim subs As Dictionary(Of String, List(Of String)) = GetDL(S, "unitSubs")
    Return subs.ContainsKey(u) AndAlso subs(u).Count > 0
End Function

Function CtxDirs(S As Dictionary(Of String, Object), ctx As String) As String()
    Dim dst As String = CStr(S("DST"))
    Dim p() As String = ctx.Split("|"c)

    Select Case p(0)
        Case "TOP"
            Dim b As String = System.IO.Path.Combine(dst, "00. 전체 조립도")
            Return New String() {b, System.IO.Path.Combine(b, "부품도"), System.IO.Path.Combine(b, "구매품")}

        Case "UNIT"
            Dim b As String = System.IO.Path.Combine(dst, p(1))
            If UnitHasSub(S, p(1)) Then
                Return New String() {System.IO.Path.Combine(b, "01. 조립도"), _
                                     System.IO.Path.Combine(b, "03. 부품도"), _
                                     System.IO.Path.Combine(b, "04. 구매품")}
            End If
            Return New String() {System.IO.Path.Combine(b, "01. 조립도"), _
                                 System.IO.Path.Combine(b, "02. 부품도"), _
                                 System.IO.Path.Combine(b, "03. 구매품")}

        Case "SUB"
            Dim sb As String = SubDir(S, p(1), p(2))
            Return New String() {System.IO.Path.Combine(sb, "01. 조립도"), _
                                 System.IO.Path.Combine(sb, "02. 부품도"), _
                                 System.IO.Path.Combine(sb, "03. 구매품")}

        Case "GRP"
            Return New String() {p(1), p(1), System.IO.Path.Combine(p(1), "구매품")}

        Case Else
            Dim b As String = System.IO.Path.Combine(dst, p(1))
            Return New String() {b, b, System.IO.Path.Combine(b, "구매품")}
    End Select
End Function

Function SubDir(S As Dictionary(Of String, Object), u As String, subName As String) As String
    Return System.IO.Path.Combine(CStr(S("DST")), u, "02. 하부조립도", subName)
End Function

Function LocCtx(S As Dictionary(Of String, Object), f As String) As String()
    Dim segs() As String = RelSegs(f, CStr(S("SRC")))
    Dim u As String = segs(0)
    If segs.Length >= 4 AndAlso DirKind(S, segs(1)) = "SUBS" Then
        Return New String() {"SUB|" & u & "|" & segs(2), "3"}
    End If
    If segs.Length >= 3 AndAlso IsSubUnitDir(S, segs(1)) Then
        Return New String() {"SUB|" & u & "|" & segs(1), "2"}
    End If
    Return New String() {"UNIT|" & u, "1"}
End Function

Function MapUnitFile(S As Dictionary(Of String, Object), f As String) As String()
    Dim segs() As String = RelSegs(f, CStr(S("SRC")))
    Dim u As String = segs(0)
    Dim nm As String = System.IO.Path.GetFileName(f)

    Dim moveSub As Dictionary(Of String, String) = GetDict(S, "moveSub")
    If moveSub.ContainsKey(f) Then
        Dim mc As String = "SUB|" & u & "|" & moveSub(f)
        Return New String() {mc, System.IO.Path.Combine(CtxDirs(S, mc)(0), nm), "하부 유닛 조립도라 그 하부 유닛 조립도 폴더로"}
    End If

    Dim lc() As String = LocCtx(S, f)
    Dim ctx As String = lc(0)
    Dim i As Integer = CInt(lc(1))
    Dim cd() As String = CtxDirs(S, ctx)

    Dim baseDir As String
    If ctx.StartsWith("SUB|") Then
        baseDir = SubDir(S, u, ctx.Split("|"c)(2))
    Else
        baseDir = System.IO.Path.Combine(CStr(S("DST")), u)
    End If

    Dim remain As Integer = segs.Length - i
    If remain = 1 Then
        If Ext(f) = ".iam" Then Return New String() {ctx, System.IO.Path.Combine(cd(0), nm), ""}
        Return New String() {ctx, System.IO.Path.Combine(cd(1), nm), ""}
    End If

    Dim rest As String = String.Join("\", segs, i + 1, segs.Length - i - 1)
    Select Case DirKind(S, segs(i))
        Case "ASM"
            Return New String() {ctx, System.IO.Path.Combine(cd(0), rest), ""}
        Case "PART"
            Return New String() {ctx, System.IO.Path.Combine(cd(1), rest), ""}
        Case Else
            Return New String() {ctx, System.IO.Path.Combine(baseDir, String.Join("\", segs, i, remain)), _
                                 "분류 폴더(조립도 / 부품도 / 가공품)가 아니라 원래 구조 그대로"}
    End Select
End Function

Function GetCtx(S As Dictionary(Of String, Object), f As String) As String
    Dim memo As Dictionary(Of String, String) = GetDict(S, "ctxMemo")
    If memo.ContainsKey(f) Then Return memo(f)
    memo(f) = ""
    Dim c As String = ComputeCtx(S, f)
    memo(f) = c
    Return c
End Function

Function ComputeCtx(S As Dictionary(Of String, Object), f As String) As String
    Dim srcRoot As String = CStr(S("SRC"))

    If CBool(S("TOPMODE")) AndAlso String.Equals(f, CStr(S("HOST")), StringComparison.OrdinalIgnoreCase) Then
        Return "TOP"
    End If

    If Not IsUnder(f, srcRoot) Then
        Dim sc As String = StructCtx(S, f)
        Dim ep As Dictionary(Of String, String) = GetDict(S, "extParent")
        Dim prj As String = ProjectOf(f)
        If prj = "" Then prj = "도번 없음"

        If Ext(f) = ".iam" AndAlso ep.ContainsKey(f) AndAlso Not IsOutside(S, ep(f)) Then
            Dim gBase As String
            Dim pp() As String = (sc & "|").Split("|"c)
            If pp(0) = "UNIT" OrElse pp(0) = "SUB" Then
                gBase = System.IO.Path.Combine(CStr(S("DST")), pp(1), CStr(S("OTHERDIR")))
            Else
                gBase = System.IO.Path.Combine(CtxDirs(S, "TOP")(0), CStr(S("OTHERDIR")))
            End If
            Dim g As String = System.IO.Path.Combine(gBase, System.IO.Path.GetFileNameWithoutExtension(f))
            If Not GetList(S, "otherGroups").Contains(g) Then GetList(S, "otherGroups").Add(g)
            Warn(S, f, "다른 프로젝트 조립도(" & prj & ") - " & CStr(S("OTHERDIR")) & " 에 묶음으로 (사용 : " & _
                       System.IO.Path.GetFileName(ep(f)) & ")")
            Return "GRP|" & g
        End If

        If ep.ContainsKey(f) Then
            Warn(S, f, "원본 폴더 밖 가공품(" & prj & ") - 이것을 조립한 " & System.IO.Path.GetFileName(ep(f)) & " 와 같은 폴더로")
        Else
            Warn(S, f, "원본 폴더 밖 파일 - 쓰는 조립도를 못 찾음")
        End If
        If sc = "" Then Return "TOP"
        Return sc
    End If

    Dim segs() As String = RelSegs(f, srcRoot)
    If segs.Length = 1 Then Return "TOP"
    If InList(CfgList(S, "ASIS"), segs(0)) Then Return "ASIS|" & segs(0)
    Return MapUnitFile(S, f)(0)
End Function

Function StructCtx(S As Dictionary(Of String, Object), f As String) As String
    For Each par As String In ParentsOf(S, f)
        If PurchInfo(S, par) IsNot Nothing Then Continue For
        Dim c As String = GetCtx(S, par)
        If c = "" Then Continue For
        GetDict(S, "extParent")(f) = par
        If c.StartsWith("ASIS|") Then Return "TOP"
        Return c
    Next
    Return ""
End Function

Function DestOf(S As Dictionary(Of String, Object), f As String) As String
    Dim primary As Dictionary(Of String, String) = GetDict(S, "primary")
    If primary.ContainsKey(f) Then Return primary(f)
    Dim memo As Dictionary(Of String, String) = GetDict(S, "destMemo")
    If memo.ContainsKey(f) Then Return memo(f)
    memo(f) = ""
    Dim d As String = NormalDest(S, f, GetCtx(S, f))
    memo(f) = d
    Return d
End Function

Function NormalDest(S As Dictionary(Of String, Object), f As String, ctx As String) As String
    Dim srcRoot As String = CStr(S("SRC"))
    Dim dst As String = CStr(S("DST"))
    Dim nm As String = System.IO.Path.GetFileName(f)

    If ctx.StartsWith("ASIS|") Then Return System.IO.Path.Combine(dst, f.Substring(srcRoot.Length + 1))

    Dim cd() As String = CtxDirs(S, ctx)
    If ctx = "TOP" Then
        Dim inRoot As Boolean = String.Equals(System.IO.Path.GetDirectoryName(f), srcRoot, StringComparison.OrdinalIgnoreCase)
        If Ext(f) = ".iam" OrElse inRoot Then Return System.IO.Path.Combine(cd(0), nm)
        Return System.IO.Path.Combine(cd(1), nm)
    End If

    If IsUnder(f, srcRoot) Then Return MapUnitFile(S, f)(1)

    Dim ep As Dictionary(Of String, String) = GetDict(S, "extParent")
    If ctx.StartsWith("GRP|") AndAlso ep.ContainsKey(f) AndAlso Not IsOutside(S, ep(f)) Then
        Return System.IO.Path.Combine(cd(0), nm)
    End If
    If ep.ContainsKey(f) Then
        Dim pd As String = DestOf(S, ep(f))
        If pd <> "" Then Return System.IO.Path.Combine(System.IO.Path.GetDirectoryName(pd), nm)
    End If

    If Ext(f) = ".iam" Then Return System.IO.Path.Combine(cd(0), nm)
    Return System.IO.Path.Combine(cd(1), nm)
End Function

Function CategoryOf(S As Dictionary(Of String, Object), f As String, ctx As String, dst As String) As String
    If ctx.StartsWith("ASIS|") Then Return "원래구조"
    If ctx.StartsWith("GRP|") Then Return "타프로젝트"
    If IsDrawingExt(f) Then Return "도면"
    Dim cd() As String = CtxDirs(S, ctx)
    If IsUnder(dst, cd(0)) Then Return "조립도"
    If IsUnder(dst, cd(1)) Then Return "부품도"
    If ctx = "TOP" Then Return "조립도"
    Return "원래구조"
End Function

Function AddPlan(S As Dictionary(Of String, Object), kind As String, src As String, dst As String, _
                 cat As String, buy As String, note As String) As String
    Dim owner As Dictionary(Of String, String) = GetDict(S, "dstOwner")
    Dim finalDst As String = dst
    Dim n As Integer = 1
    Do While owner.ContainsKey(finalDst) AndAlso Not String.Equals(owner(finalDst), src, StringComparison.OrdinalIgnoreCase)
        n += 1
        finalDst = System.IO.Path.Combine(System.IO.Path.GetDirectoryName(dst), "_중복" & n, System.IO.Path.GetFileName(dst))
    Loop
    If n > 1 Then note = AddNote(note, "같은 이름의 다른 파일이 있어 _중복" & n & " 폴더로")
    If owner.ContainsKey(finalDst) Then Return finalDst
    owner(finalDst) = src
    Plan(S).Add(New String() {kind, src, finalDst, cat, buy, note})
    Return finalDst
End Function

Sub PlaceNormal(S As Dictionary(Of String, Object), f As String)
    Dim primary As Dictionary(Of String, String) = GetDict(S, "primary")
    If primary.ContainsKey(f) Then Return
    Dim ctx As String = GetCtx(S, f)
    Dim dst As String = NormalDest(S, f, ctx)
    Dim buy As String = CtxDirs(S, ctx)(2)
    If IsUnder(f, CStr(S("SRC"))) AndAlso Not ctx.StartsWith("ASIS|") AndAlso ctx <> "TOP" Then
        Dim mn As String = MapUnitFile(S, f)(2)
        If mn <> "" Then Warn(S, f, mn)
    End If
    If ctx = "TOP" AndAlso Not String.Equals(System.IO.Path.GetDirectoryName(f), CStr(S("SRC")), StringComparison.OrdinalIgnoreCase) Then
        Warn(S, f, TOP_NOTE())
    End If
    primary(f) = AddPlan(S, "N", f, dst, CategoryOf(S, f, ctx, dst), buy, WarnOf(S, f))
End Sub

Function TOP_NOTE() As String
    Return "전체 조립도에 바로 들어간 부품(유닛 밖)"
End Function

Function BuyNote(S As Dictionary(Of String, Object), buy As String) As String
    If String.Equals(buy, CtxDirs(S, "TOP")(2), StringComparison.OrdinalIgnoreCase) Then Return TOP_NOTE()
    Return ""
End Function

Sub PlacePurchased(S As Dictionary(Of String, Object), src As String, buy As String, Optional usedBy As String = "")
    Dim purchKey As Dictionary(Of String, String) = GetDict(S, "purchKey")
    Dim key As String = src & "|" & buy
    If purchKey.ContainsKey(key) Then
        MarkUsedBy(S, purchKey(key), usedBy)
        Return
    End If

    Dim pinfo() As String = PurchInfo(S, src)
    If pinfo Is Nothing Then Return
    Dim cat As String = "구매품"
    If pinfo(1).StartsWith("공용부품\") Then cat = "공용부품"

    If pinfo(0) <> "" Then PlacePackage(S, pinfo(0), buy)

    If Not purchKey.ContainsKey(key) Then
        Dim made As String = AddPlan(S, "P", src, System.IO.Path.Combine(buy, pinfo(1)), cat, buy, BuyNote(S, buy))
        purchKey(key) = made
        If pinfo(0) = "" AndAlso IsModelExt(src) Then
            For Each de As String In New String() {".idw", ".dwg"}
                Dim dp As String = System.IO.Path.ChangeExtension(src, de)
                If System.IO.File.Exists(dp) AndAlso Not IsSkipped(S, dp) Then
                    purchKey(dp & "|" & buy) = AddPlan(S, "P", dp, System.IO.Path.ChangeExtension(made, de), cat, buy, BuyNote(S, buy))
                    GetSet(S, "purchPlaced").Add(dp)
                End If
            Next
        End If
    End If
    GetSet(S, "purchPlaced").Add(src)
    MarkUsedBy(S, purchKey(key), usedBy)

    For Each c As String In ChildrenOf(S, src)
        If PurchInfo(S, c) IsNot Nothing Then
            PlacePurchased(S, c, buy, System.IO.Path.GetFileName(src))
        Else
            PlaceNormal(S, c)
        End If
    Next
End Sub

Sub MarkUsedBy(S As Dictionary(Of String, Object), dst As String, usedBy As String)
    If usedBy = "" Then Return
    Dim ub As Dictionary(Of String, String) = GetDict(S, "usedBy")
    If Not ub.ContainsKey(dst) Then
        ub(dst) = usedBy
    ElseIf Not ub(dst).Contains(usedBy) Then
        ub(dst) = ub(dst) & ", " & usedBy
    End If
End Sub

Sub PlacePackage(S As Dictionary(Of String, Object), pkgRoot As String, buy As String)
    Dim done As HashSet(Of String) = GetSet(S, "pkgDone")
    Dim key As String = pkgRoot & "|" & buy
    If done.Contains(key) Then Return
    done.Add(key)

    Dim dirOwner As Dictionary(Of String, String) = GetDict(S, "pkgDirOwner")
    Dim pkgName As String = System.IO.Path.GetFileName(pkgRoot)
    Dim dir As String = System.IO.Path.Combine(buy, pkgName)
    Dim n As Integer = 1
    Do While dirOwner.ContainsKey(dir) AndAlso Not String.Equals(dirOwner(dir), pkgRoot, StringComparison.OrdinalIgnoreCase)
        n += 1
        dir = System.IO.Path.Combine(buy, pkgName & "_중복" & n)
    Loop
    dirOwner(dir) = pkgRoot
    Dim note As String = BuyNote(S, buy)
    If n > 1 Then note = AddNote(note, "같은 이름의 다른 품번 폴더가 있어 " & System.IO.Path.GetFileName(dir) & " 로")

    Dim cat As String = "구매품"
    Dim purchKey As Dictionary(Of String, String) = GetDict(S, "purchKey")
    For Each f As String In EnumFiles(S, pkgRoot)
        Dim rel As String = f.Substring(pkgRoot.Length + 1)
        purchKey(f & "|" & buy) = AddPlan(S, "P", f, System.IO.Path.Combine(dir, rel), cat, buy, note)
        GetSet(S, "purchPlaced").Add(f)
    Next
End Sub

Sub MakePlan(S As Dictionary(Of String, Object))
    Dim srcRoot As String = CStr(S("SRC"))
    Dim topMode As Boolean = CBool(S("TOPMODE"))
    Dim primary As Dictionary(Of String, String) = GetDict(S, "primary")
    Dim graph As List(Of String) = GetList(S, "graph")
    Dim graphSet As HashSet(Of String) = GetSet(S, "graphSet")

    For Each f As String In graph
        If PurchInfo(S, f) IsNot Nothing Then Continue For
        PlaceNormal(S, f)
    Next

    For Each f As String In graph
        If PurchInfo(S, f) IsNot Nothing Then Continue For
        Dim buy As String = CtxDirs(S, GetCtx(S, f))(2)
        For Each c As String In ChildrenOf(S, f)
            If PurchInfo(S, c) IsNot Nothing Then PlacePurchased(S, c, buy, System.IO.Path.GetFileName(f))
        Next
    Next

    Dim unitFiles As Dictionary(Of String, List(Of String)) = GetDL(S, "unitFiles")
    For Each u As String In CType(S("targets"), List(Of String))
        If Not unitFiles.ContainsKey(u) Then Continue For
        For Each f As String In unitFiles(u)
            If primary.ContainsKey(f) Then Continue For
            If PurchInfo(S, f) IsNot Nothing Then
                If graphSet.Contains(f) OrElse GetSet(S, "purchPlaced").Contains(f) Then Continue For
                PlacePurchased(S, f, CtxDirs(S, LocCtx(S, f)(0))(2))
                Continue For
            End If
            PlaceNormal(S, f)
        Next
    Next

    Dim drawCands As New List(Of String)
    If topMode Then
        For Each f As String In System.IO.Directory.GetFiles(srcRoot)
            If IsSkipped(S, f) OrElse primary.ContainsKey(f) Then Continue For
            If IsDrawingExt(f) Then
                drawCands.Add(f)
                Continue For
            End If
            PlaceNormal(S, f)
        Next

        For Each a As String In CfgList(S, "ASIS")
            Dim ad As String = System.IO.Path.Combine(srcRoot, a)
            If Not System.IO.Directory.Exists(ad) Then Continue For
            For Each f As String In EnumFiles(S, ad)
                PlaceNormal(S, f)
            Next
        Next
    End If

    Dim models As New List(Of String)(primary.Keys)
    For Each m As String In models
        If Not IsModelExt(m) Then Continue For
        For Each de As String In New String() {".idw", ".dwg"}
            Dim dp As String = System.IO.Path.ChangeExtension(m, de)
            If System.IO.File.Exists(dp) AndAlso Not IsSkipped(S, dp) Then drawCands.Add(dp)
        Next
    Next

    For Each dp As String In drawCands
        If primary.ContainsKey(dp) Then Continue For
        If PurchInfo(S, dp) IsNot Nothing Then Continue For

        Dim segs() As String = New String() {}
        If IsUnder(dp, srcRoot) Then segs = RelSegs(dp, srcRoot)
        If segs.Length > 1 Then
            PlaceNormal(S, dp)
            Continue For
        End If

        Dim modelDst As String = ""
        Dim modelSrc As String = ""
        For Each me2 As String In New String() {".ipt", ".iam"}
            Dim mp As String = System.IO.Path.ChangeExtension(dp, me2)
            If primary.ContainsKey(mp) Then
                modelDst = primary(mp)
                modelSrc = mp
                Exit For
            End If
        Next
        If modelDst <> "" Then
            primary(dp) = AddPlan(S, "N", dp, _
                                  System.IO.Path.Combine(System.IO.Path.GetDirectoryName(modelDst), System.IO.Path.GetFileName(dp)), _
                                  "도면", CtxDirs(S, GetCtx(S, modelSrc))(2), "")
        Else
            PlaceNormal(S, dp)
        End If
    Next
End Sub

Function PlanSummary(S As Dictionary(Of String, Object)) As String
    Dim counts As New Dictionary(Of String, Integer)
    Dim order As New List(Of String)
    For Each it As String() In Plan(S)
        If Not counts.ContainsKey(it(3)) Then
            counts(it(3)) = 0
            order.Add(it(3))
        End If
        counts(it(3)) += 1
    Next

    Dim nWarn As Integer = 0
    Dim nTop As Integer = 0
    For Each it As String() In Plan(S)
        If it(5) <> "" Then nWarn += 1
        If it(5).Contains(TOP_NOTE()) Then nTop += 1
    Next

    Dim msg As String = ""
    If CBool(S("TOPMODE")) Then
        msg &= "범위 : 전체 조립도 (유닛 " & GetList(S, "units").Count & "개)" & vbCrLf
    Else
        msg &= "범위 : " & CType(S("targets"), List(Of String))(0) & " 유닛만 (시험용)" & vbCrLf
    End If
    msg &= "옮길 파일 : " & Plan(S).Count & "개" & vbCrLf
    For Each k As String In order
        msg &= "   " & k & " : " & counts(k) & vbCrLf
    Next
    msg &= "확인할 것(비고 있음) : " & nWarn & "개" & vbCrLf
    If nTop > 0 Then
        msg &= "  ※ 유닛 밖, 전체 조립도에 바로 들어간 부품 : " & nTop & "개 -> 00. 전체 조립도 안에 넣음" & vbCrLf
    End If
    msg &= "원본에서 이미 끊긴 참조 : " & GetList(S, "missing").Count & "개" & vbCrLf

    Dim tg As List(Of String) = CType(S("targets"), List(Of String))
    Dim codes As String = ""
    For Each u As String In tg
        Dim subs As New List(Of String)
        If GetDL(S, "unitSubs").ContainsKey(u) Then subs = GetDL(S, "unitSubs")(u)
        If subs.Count = 0 Then
            codes &= "   " & u & " : 하부조립도 없음 (01. 조립도 / 02. 부품도 / 03. 구매품)" & vbCrLf
        Else
            codes &= "   " & u & " : 하부 유닛 " & subs.Count & "개 - " & String.Join(", ", subs.ToArray()) & vbCrLf
        End If
    Next
    msg &= vbCrLf & "유닛 구성" & vbCrLf & codes

    Dim ubs As Dictionary(Of String, String) = GetDict(S, "usedBy")
    Dim lvl As String = ""
    Dim nLvl As Integer = 0
    For Each u As String In tg
        If Not UnitHasSub(S, u) Then Continue For
        Dim ud() As String = CtxDirs(S, "UNIT|" & u)
        For Each it As String() In Plan(S)
            If Not (IsUnder(it(2), ud(1)) OrElse IsUnder(it(2), ud(2))) Then Continue For
            nLvl += 1
            If nLvl > 15 Then Continue For
            Dim why As String = ""
            If ubs.ContainsKey(it(2)) Then why = "  <- 사용 : " & ubs(it(2))
            lvl &= "   " & it(2).Substring(CStr(S("DST")).Length + 1) & why & vbCrLf
        Next
    Next
    If nLvl > 0 Then
        msg &= vbCrLf & "하부 유닛이 있는데 유닛 레벨 부품도 / 구매품에 들어간 파일 : " & nLvl & "개" & vbCrLf & lvl
        If nLvl > 15 Then msg &= "   ... 나머지는 CSV 에서 확인" & vbCrLf
    End If

    Dim grps As List(Of String) = GetList(S, "otherGroups")
    If grps.Count > 0 Then
        msg &= vbCrLf & "다른 프로젝트에서 통째로 가져온 조립도 묶음 : " & grps.Count & "개" & vbCrLf
        For Each g As String In grps
            msg &= "   " & g.Substring(CStr(S("DST")).Length + 1) & vbCrLf
        Next
    End If

    Dim temps As String = ""
    For Each t As String In GetList(S, "tempSubNames")
        If StartsWithUnit(t, tg) Then temps &= "   " & t & vbCrLf
    Next
    If temps <> "" Then
        msg &= vbCrLf & "원본에 하부 유닛 폴더가 없어 임시 이름을 붙인 곳 (직접 이름을 바꾸세요)" & vbCrLf & temps
    End If
    Return msg
End Function

Function StartsWithUnit(t As String, units As List(Of String)) As Boolean
    For Each u As String In units
        If t.StartsWith(u & " ") Then Return True
    Next
    Return False
End Function

Sub WritePlanCsv(S As Dictionary(Of String, Object), csvPath As String)
    Dim sb As New System.Text.StringBuilder()
    sb.AppendLine("분류,새 위치,원본,비고")

    Dim rows As New List(Of String())(Plan(S))
    rows.Sort(Function(a As String(), b As String()) String.Compare(a(2), b(2), StringComparison.OrdinalIgnoreCase))
    Dim ub As Dictionary(Of String, String) = GetDict(S, "usedBy")
    For Each it As String() In rows
        Dim note As String = it(5)
        If ub.ContainsKey(it(2)) Then note = AddNote(note, "사용 : " & ub(it(2)))
        sb.AppendLine(CsvField(it(3)) & "," & CsvField(it(2)) & "," & CsvField(it(1)) & "," & CsvField(note))
    Next
    For Each ex As String() In CType(S("excluded"), List(Of String()))
        sb.AppendLine(CsvField("제외") & "," & CsvField("") & "," & CsvField(ex(0)) & "," & CsvField(ex(1)))
    Next
    For Each m As String In GetList(S, "missing")
        Dim pp() As String = m.Split("|"c)
        sb.AppendLine(CsvField("참조 끊김") & "," & CsvField("") & "," & CsvField(pp(0)) & "," & _
                      CsvField("원본에서 이미 못 찾는 참조 : " & pp(1)))
    Next
    System.IO.File.WriteAllText(csvPath, sb.ToString(), New System.Text.UTF8Encoding(True))
End Sub

Function ExecuteCopy(S As Dictionary(Of String, Object)) As String
    Dim TTL As String = CStr(S("TTL"))
    Dim dst As String = CStr(S("DST"))
    Dim logDir As String = CStr(S("LOGDIR"))
    Dim graphSet As HashSet(Of String) = GetSet(S, "graphSet")
    Dim hasRefs As HashSet(Of String) = GetSet(S, "hasRefs")

    Dim mk As New List(Of String)
    Dim ipjDirs As New List(Of String)
    If CBool(S("TOPMODE")) Then mk.Add(CtxDirs(S, "TOP")(0))
    For Each u As String In CType(S("targets"), List(Of String))
        Dim ud() As String = CtxDirs(S, "UNIT|" & u)
        mk.Add(ud(0))
        If Not UnitHasSub(S, u) Then
            mk.Add(ud(1)) : mk.Add(ud(2))
        End If
        ipjDirs.Add(System.IO.Path.Combine(dst, u))
        If GetDL(S, "unitSubs").ContainsKey(u) Then
            For Each nn As String In GetDL(S, "unitSubs")(u)
                Dim sd() As String = CtxDirs(S, "SUB|" & u & "|" & nn)
                mk.Add(sd(1)) : mk.Add(sd(2))
                ipjDirs.Add(SubDir(S, u, nn))
            Next
        End If
    Next

    Dim failed As New List(Of String)
    For Each m As String In mk
        Try
            System.IO.Directory.CreateDirectory(m)
        Catch ex As Exception
            failed.Add("폴더 " & m & " : " & ex.Message)
        End Try
    Next

    Dim nCopied As Integer = 0
    Dim nExists As Integer = 0
    Dim items As List(Of String()) = Plan(S)
    Dim prog As System.Windows.Forms.Form = ProgOpen(TTL & " - 복사")
    Dim sw As New System.Diagnostics.Stopwatch()
    sw.Start()
    Dim copyStopped As Boolean = False
    For i As Integer = 0 To items.Count - 1
        If i Mod 10 = 0 Then
            If ProgStopped(prog) Then
                copyStopped = True
                Exit For
            End If
            ThisApplication.StatusBarText = TTL & " : 복사 " & i & " / " & items.Count
            ProgSet(prog, i, items.Count, System.IO.Path.GetFileName(items(i)(2)), _
                    "복사 " & nCopied & "   이미 있어 건너뜀 " & nExists & "   실패 " & failed.Count, sw)
        End If
        Dim r As String = CopyFileSafe(items(i)(1), items(i)(2))
        If r = "copied" Then
            nCopied += 1
        ElseIf r = "exists" Then
            nExists += 1
        Else
            failed.Add(items(i)(1) & " : " & r)
            ProgLine(prog, "복사 실패   " & System.IO.Path.GetFileName(items(i)(1)) & "   " & r)
        End If
    Next
    ThisApplication.StatusBarText = ""
    If copyStopped Then
        ProgClose(prog)
        Return "복사를 중지했습니다. 복사 : " & nCopied & "개, 이미 있어 건너뜀 : " & nExists & "개" & vbCrLf & vbCrLf & _
               "다시 2. 복사 를 실행하면 남은 것부터 이어서 복사합니다." & vbCrLf & _
               "(재연결 목록은 복사를 끝까지 마쳐야 만들어집니다)"
    End If
    ProgSet(prog, items.Count, items.Count, "프로젝트 파일 / 재연결 목록 만드는 중...", _
            "복사 " & nCopied & "   이미 있어 건너뜀 " & nExists & "   실패 " & failed.Count, sw)

    Dim ipjMsg As String = ""
    Dim rootIpj As String = System.IO.Path.Combine(dst, CStr(S("ROOTNAME")) & ".ipj")
    If Not System.IO.File.Exists(rootIpj) Then
        Try
            Dim proj As Inventor.DesignProject = ThisApplication.DesignProjectManager.DesignProjects.Add( _
                Inventor.MultiUserModeEnum.kSingleUserMode, CStr(S("ROOTNAME")), dst)
            ipjMsg &= "프로젝트 생성 : " & proj.FullFileName & vbCrLf & _
                      "   작업공간 : " & proj.WorkspacePath & vbCrLf
            If Not System.IO.File.Exists(rootIpj) AndAlso System.IO.File.Exists(proj.FullFileName) Then
                rootIpj = proj.FullFileName
            End If
        Catch ex As Exception
            ipjMsg &= "프로젝트 파일을 만들지 못했습니다 : " & ex.Message & vbCrLf & _
                      "   직접 만드세요 : " & rootIpj & " (작업공간 = 그 폴더)" & vbCrLf
        End Try
    Else
        ipjMsg &= "프로젝트 파일이 이미 있어 그대로 둠 : " & rootIpj & vbCrLf
    End If

    Dim nIpj As Integer = 0
    If System.IO.File.Exists(rootIpj) Then
        For Each pd As String In ipjDirs
            Dim ip As String = System.IO.Path.Combine(pd, System.IO.Path.GetFileName(pd) & ".ipj")
            Dim r As String = CopyFileSafe(rootIpj, ip)
            If r = "copied" Then
                nIpj += 1
            ElseIf r <> "exists" Then
                failed.Add(ip & " : " & r)
            End If
        Next
        ipjMsg &= "유닛 / 하부 유닛 프로젝트 파일 : " & nIpj & "개" & vbCrLf
    End If

    Dim depthMemo As Dictionary(Of String, Integer) = New Dictionary(Of String, Integer)(StringComparer.OrdinalIgnoreCase)
    Dim jobs As New System.Text.StringBuilder()
    Dim map As New System.Text.StringBuilder()
    Dim nJobs As Integer = 0
    For Each it As String() In items
        map.AppendLine(it(0) & vbTab & it(1) & vbTab & it(2) & vbTab & it(4))

        Dim fe As String = Ext(it(2))
        If fe <> ".ipt" AndAlso fe <> ".iam" AndAlso fe <> ".idw" AndAlso fe <> ".dwg" Then Continue For
        If fe = ".ipt" AndAlso graphSet.Contains(it(1)) AndAlso Not hasRefs.Contains(it(1)) Then Continue For

        Dim ord As Integer = 0
        If fe = ".iam" Then
            ord = 1
            If graphSet.Contains(it(1)) Then ord = 1 + Depth(S, it(1), depthMemo, NewSet())
        ElseIf fe = ".idw" OrElse fe = ".dwg" Then
            ord = 1000
        End If
        jobs.AppendLine(ord & vbTab & it(2) & vbTab & it(4) & vbTab & If(graphSet.Contains(it(1)), "1", "0"))
        nJobs += 1
    Next

    Try
        System.IO.Directory.CreateDirectory(logDir)
        System.IO.File.WriteAllText(System.IO.Path.Combine(logDir, "copy_map.tsv"), map.ToString(), New System.Text.UTF8Encoding(True))
        System.IO.File.WriteAllText(System.IO.Path.Combine(logDir, "relink_jobs.tsv"), jobs.ToString(), New System.Text.UTF8Encoding(True))
    Catch ex As Exception
        failed.Add("작업 목록 저장 실패 : " & ex.Message)
    End Try

    If failed.Count > 0 Then
        Try
            System.IO.File.WriteAllLines(System.IO.Path.Combine(logDir, "복사실패_" & DateTime.Now.ToString("yyyyMMdd_HHmmss") & ".txt"), _
                                         failed.ToArray(), New System.Text.UTF8Encoding(True))
        Catch
        End Try
    End If

    Dim msg As String = "복사 : " & nCopied & "개,  이미 있어 건너뜀 : " & nExists & "개,  실패 : " & failed.Count & "개" & vbCrLf
    msg &= ipjMsg
    msg &= "재연결할 파일 : " & nJobs & "개" & vbCrLf & vbCrLf
    If failed.Count > 0 Then
        msg &= "실패 목록은 " & logDir & " 의 복사실패_*.txt 에 있습니다." & vbCrLf & vbCrLf
    End If
    ProgClose(prog)
    msg &= "아직 복사본의 참조는 원본을 보고 있습니다. 이어서 재연결하세요." & vbCrLf & _
           "  1) 인벤터에서 모든 파일 닫기" & vbCrLf & _
           "  2) 프로젝트 창에서 " & System.IO.Path.GetFileName(rootIpj) & " 활성화" & vbCrLf & _
           "     (작업공간이 " & dst & " 인지 확인)" & vbCrLf & _
           "  3) 새 부품(빈 ipt) 하나 열기 - 저장하지 않아도 됨" & vbCrLf & _
           "  4) 이 규칙 실행 -> 3. 재연결"
    Return msg
End Function

Function Depth(S As Dictionary(Of String, Object), f As String, memo As Dictionary(Of String, Integer), guard As HashSet(Of String)) As Integer
    If memo.ContainsKey(f) Then Return memo(f)
    If guard.Contains(f) Then Return 0
    guard.Add(f)
    Dim dep As Integer = 0
    For Each c As String In ChildrenOf(S, f)
        If Ext(c) <> ".iam" Then Continue For
        Dim cd As Integer = Depth(S, c, memo, guard) + 1
        If cd > dep Then dep = cd
    Next
    memo(f) = dep
    Return dep
End Function

Sub DoRelink(S As Dictionary(Of String, Object))
    Dim TTL As String = CStr(S("TTL")) & " - 재연결"
    Dim dst As String = CStr(S("DST"))
    Try
        Dim aDir As String = NormDir(System.IO.Path.GetDirectoryName( _
                             ThisApplication.DesignProjectManager.ActiveDesignProject.FullFileName))
        If System.IO.File.Exists(System.IO.Path.Combine(aDir, "_정리로그", "copy_map.tsv")) Then
            dst = aDir
        Else
            Dim lastDst As String = ReadLastDst()
            If lastDst <> "" Then
                Dim cand As String = System.IO.Path.Combine(lastDst, CStr(S("ROOTNAME")))
                If System.IO.File.Exists(System.IO.Path.Combine(cand, "_정리로그", "copy_map.tsv")) Then dst = cand
            End If
        End If
    Catch
    End Try
    S("DST") = dst
    S("LOGDIR") = System.IO.Path.Combine(dst, "_정리로그")
    InitPlanState(S)
    Dim logDir As String = CStr(S("LOGDIR"))
    Dim mapPath As String = System.IO.Path.Combine(logDir, "copy_map.tsv")
    Dim jobPath As String = System.IO.Path.Combine(logDir, "relink_jobs.tsv")

    If Not System.IO.File.Exists(mapPath) OrElse Not System.IO.File.Exists(jobPath) Then
        MessageBox.Show("복사 기록이 없습니다. 먼저 2. 복사 를 실행하세요." & vbCrLf & vbCrLf & mapPath, TTL)
        Return
    End If

    Dim rootIpj As String = System.IO.Path.Combine(dst, CStr(S("ROOTNAME")) & ".ipj")
    Dim actIpj As String = ""
    Dim actWs As String = ""
    Try
        actIpj = ThisApplication.DesignProjectManager.ActiveDesignProject.FullFileName
        actWs = NormDir(ThisApplication.DesignProjectManager.ActiveDesignProject.WorkspacePath)
    Catch
    End Try
    Dim projOk As Boolean = String.Equals(actWs, dst, StringComparison.OrdinalIgnoreCase)
    If Not projOk AndAlso actIpj <> "" Then
        projOk = String.Equals(NormDir(System.IO.Path.GetDirectoryName(actIpj)), dst, StringComparison.OrdinalIgnoreCase)
    End If
    If Not projOk Then
        MessageBox.Show("새 프로젝트가 활성화되어 있지 않습니다." & vbCrLf & vbCrLf & _
                        "지금   : " & actIpj & vbCrLf & _
                        "필요   : " & rootIpj & vbCrLf & vbCrLf & _
                        "모든 파일을 닫고 프로젝트 창에서 위 ipj 를 활성화한 뒤," & vbCrLf & _
                        "새 부품(빈 ipt) 하나를 열고 다시 실행하세요.", TTL)
        Return
    End If

    Dim host As Inventor.Document = Nothing
    Try
        host = ThisApplication.ActiveDocument
    Catch
    End Try
    Dim hostPath As String = ""
    Dim hostName As String = ""
    Try
        If host IsNot Nothing Then
            hostPath = host.FullFileName
            hostName = host.DisplayName
        End If
    Catch
    End Try
    Dim openOthers As New List(Of String)
    For Each d As Inventor.Document In ThisApplication.Documents
        Try
            If d.Views.Count = 0 Then Continue For
            If d.DisplayName = hostName AndAlso d.FullFileName = hostPath Then Continue For
            openOthers.Add(d.DisplayName)
        Catch
        End Try
    Next
    If openOthers.Count > 0 OrElse IsUnder(hostPath, dst) Then
        MessageBox.Show("다른 파일이 열려 있습니다. 모두 닫고 새 부품(빈 ipt) 하나만 연 상태에서 실행하세요." & vbCrLf & vbCrLf & _
                        String.Join(vbCrLf, openOthers.ToArray()) & If(IsUnder(hostPath, dst), vbCrLf & hostPath, ""), TTL)
        Return
    End If

    Dim primary As Dictionary(Of String, String) = NewDict()
    Dim purchKey As Dictionary(Of String, String) = NewDict()
    Dim purchAny As Dictionary(Of String, String) = NewDict()
    Dim reverse As Dictionary(Of String, String) = NewDict()
    Dim nameIndex As New Dictionary(Of String, List(Of String))(StringComparer.OrdinalIgnoreCase)

    For Each ln As String In System.IO.File.ReadAllLines(mapPath, System.Text.Encoding.UTF8)
        Dim t() As String = ln.Split(ControlChars.Tab)
        If t.Length < 4 Then Continue For
        If t(0) = "P" Then
            purchKey(t(1) & "|" & t(3)) = t(2)
            If Not purchAny.ContainsKey(t(1)) Then purchAny(t(1)) = t(2)
        ElseIf Not primary.ContainsKey(t(1)) Then
            primary(t(1)) = t(2)
        End If
        reverse(t(2)) = t(1)
        Dim nm As String = System.IO.Path.GetFileName(t(1))
        If Not nameIndex.ContainsKey(nm) Then nameIndex(nm) = New List(Of String)
        If Not nameIndex(nm).Contains(t(1)) Then nameIndex(nm).Add(t(1))
    Next
    S("r_primary") = primary
    S("r_purchKey") = purchKey
    S("r_purchAny") = purchAny
    S("r_reverse") = reverse
    S("r_nameIndex") = nameIndex
    S("r_extra") = New List(Of String)
    S("r_newJobs") = New List(Of String())

    Dim jobs As New List(Of String())
    For Each ln As String In System.IO.File.ReadAllLines(jobPath, System.Text.Encoding.UTF8)
        Dim t() As String = ln.Split(ControlChars.Tab)
        If t.Length < 3 Then Continue For
        jobs.Add(t)
    Next
    jobs.Sort(Function(a As String(), b As String()) CInt(a(0)).CompareTo(CInt(b(0))))

    Dim ask As String = "재연결할 파일 : " & jobs.Count & "개" & vbCrLf & vbCrLf & _
                        "결과 위치(" & dst & ") 의 파일만 열고 저장합니다." & vbCrLf & _
                        "파일 수에 따라 시간이 걸립니다. 진행할까요?"
    If MessageBox.Show(ask, TTL, MessageBoxButtons.OKCancel) <> DialogResult.OK Then Return

    Dim logSb As New System.Text.StringBuilder()
    logSb.AppendLine("결과,파일,옛 참조,새 참조,메시지")
    Dim nDone As Integer = 0
    Dim nSaved As Integer = 0
    Dim nRepl As Integer = 0
    Dim nFail As Integer = 0
    Dim nLeft As Integer = 0
    Dim nLeftUsed As Integer = 0

    Dim prevSilent As Boolean = ThisApplication.SilentOperation
    Dim prog As System.Windows.Forms.Form = ProgOpen(TTL)
    Dim sw As New System.Diagnostics.Stopwatch()
    sw.Start()
    Dim stopped As Boolean = False
    Try
        ThisApplication.SilentOperation = True

        Dim ji As Integer = -1
        Do While ji + 1 < jobs.Count
            ji += 1
            Dim jf As String = jobs(ji)(1)
            Dim buy As String = jobs(ji)(2)
            Dim used As String = "?"
            If jobs(ji).Length > 3 Then used = jobs(ji)(3)
            ThisApplication.StatusBarText = TTL & " : " & (ji + 1) & " / " & jobs.Count & "  " & System.IO.Path.GetFileName(jf)
            If ProgStopped(prog) Then
                stopped = True
                logSb.AppendLine(CsvField("중지") & ",,,," & CsvField("사용자가 중지함 - 다시 실행하면 남은 것부터 이어서 됨"))
                Exit Do
            End If
            ProgSet(prog, ji, jobs.Count, System.IO.Path.GetFileName(jf), _
                    "대체 " & nRepl & "   저장 " & nSaved & "   못 찾음 " & nLeft & " (조립에 쓰이는 " & nLeftUsed & ")   실패 " & nFail, sw)
            Dim replBefore As Integer = nRepl

            If Not IsUnder(jf, dst) Then
                logSb.AppendLine(CsvField("건너뜀") & "," & CsvField(jf) & ",,," & CsvField("결과 폴더 밖 파일"))
                Continue Do
            End If
            If Not System.IO.File.Exists(jf) Then
                logSb.AppendLine(CsvField("없음") & "," & CsvField(jf) & ",,," & CsvField("복사본이 없음"))
                nFail += 1
                Continue Do
            End If
            If Ext(jf) = ".dwg" Then
                Dim isInv As Boolean = False
                Try
                    isInv = ThisApplication.FileManager.IsInventorDWG(jf)
                Catch
                End Try
                If Not isInv Then Continue Do
            End If

            Dim doc As Inventor.Document = Nothing
            Try
                Dim opts As Inventor.NameValueMap = ThisApplication.TransientObjects.CreateNameValueMap()
                opts.Add("SkipAllUnresolvedFiles", True)
                doc = ThisApplication.Documents.OpenWithOptions(jf, opts, False)
            Catch ex As Exception
                logSb.AppendLine(CsvField("열기 실패") & "," & CsvField(jf) & ",,," & CsvField(ex.Message))
                nFail += 1
                ProgLine(prog, "열기 실패   " & System.IO.Path.GetFileName(jf) & "   " & ex.Message)
                Continue Do
            End Try

            Dim fds As New List(Of Inventor.FileDescriptor)
            Try
                For Each fd As Inventor.FileDescriptor In doc.File.ReferencedFileDescriptors
                    fds.Add(fd)
                Next
            Catch
            End Try

            Dim changed As Boolean = False
            For Each fd As Inventor.FileDescriptor In fds
                Dim oldRef As String = ""
                Try
                    oldRef = fd.FullFileName
                Catch
                    Continue For
                End Try

                Dim target As String = MapRef(S, oldRef, buy, jf, used)
                If target = "" Then
                    Dim resolved As Boolean = False
                    Try
                        resolved = Not fd.ReferenceMissing
                    Catch
                    End Try
                    If Not (resolved AndAlso IsUnder(oldRef, dst)) Then
                        Dim why As String
                        If System.IO.File.Exists(oldRef) OrElse System.IO.File.Exists(OtherDrive(S, oldRef)) Then
                            why = "원본은 있지만 가져오지 못함"
                        Else
                            why = "원본 파일이 없음 (옛 경로 / 내려받기 안 됨 / 지워짐) - 원본에서도 끊겨 있던 참조"
                        End If
                        Dim kind As String = "못 찾음(안 쓰는 파일)"
                        If used <> "0" Then
                            kind = "못 찾음(조립에 쓰이는 파일)"
                            nLeftUsed += 1
                        End If
                        logSb.AppendLine(CsvField(kind) & "," & CsvField(jf) & "," & CsvField(oldRef) & ",," & CsvField(why))
                        nLeft += 1
                        If used <> "0" Then
                            ProgLine(prog, "못 찾음     " & System.IO.Path.GetFileName(jf) & "  ->  " & System.IO.Path.GetFileName(oldRef))
                        End If
                    End If
                    Continue For
                End If
                If String.Equals(target, oldRef, StringComparison.OrdinalIgnoreCase) Then
                    Dim missingNow As Boolean = False
                    Try
                        missingNow = fd.ReferenceMissing
                    Catch
                    End Try
                    If Not missingNow Then Continue For
                End If

                Try
                    fd.ReplaceReference(target)
                    changed = True
                    nRepl += 1
                Catch ex As Exception
                    logSb.AppendLine(CsvField("대체 실패") & "," & CsvField(jf) & "," & CsvField(oldRef) & "," & _
                                   CsvField(target) & "," & CsvField(ex.Message))
                    nFail += 1
                    ProgLine(prog, "대체 실패   " & System.IO.Path.GetFileName(jf) & "  ->  " & System.IO.Path.GetFileName(oldRef))
                End Try
            Next

            If changed Then
                Try
                    doc.Save2(False)
                    nSaved += 1
                    logSb.AppendLine(CsvField("저장") & "," & CsvField(jf) & ",,,")
                    ProgLine(prog, "연결 완료   " & System.IO.Path.GetFileName(jf) & "   (참조 " & (nRepl - replBefore) & "개 바꿈)")
                Catch ex As Exception
                    logSb.AppendLine(CsvField("저장 실패") & "," & CsvField(jf) & ",,," & CsvField(ex.Message))
                    nFail += 1
                    ProgLine(prog, "저장 실패   " & System.IO.Path.GetFileName(jf) & "   " & ex.Message)
                End Try
            End If

            Try
                doc.Close(True)
            Catch
            End Try
            nDone += 1
            If nDone Mod 20 = 0 Then CloseHiddenDocs()

            Dim nj As List(Of String()) = CType(S("r_newJobs"), List(Of String()))
            For Each x As String() In nj
                ProgLine(prog, "추가 복사   " & System.IO.Path.GetFileName(x(1)) & "   (재연결 목록에 추가)")
            Next
            jobs.AddRange(nj)
            nj.Clear()
        Loop
        If Not stopped Then
            ProgSet(prog, jobs.Count, jobs.Count, "끝", _
                    "대체 " & nRepl & "   저장 " & nSaved & "   못 찾음 " & nLeft & " (조립에 쓰이는 " & nLeftUsed & ")   실패 " & nFail, sw)
        End If

    Catch ex As Exception
        logSb.AppendLine(CsvField("중단") & ",,,," & CsvField(ex.Message))
        nFail += 1
    Finally
        ThisApplication.SilentOperation = prevSilent
        ThisApplication.StatusBarText = ""
    End Try
    CloseHiddenDocs()

    For Each x As String In GetList(S, "r_extra")
        logSb.AppendLine(CsvField("추가 복사") & "," & CsvField(x) & ",,," & CsvField("복사 목록에 없던 파일을 재연결 중에 복사"))
    Next

    Dim logPath As String = System.IO.Path.Combine(logDir, "재연결_" & DateTime.Now.ToString("yyyyMMdd_HHmmss") & ".csv")
    Try
        System.IO.File.WriteAllText(logPath, logSb.ToString(), New System.Text.UTF8Encoding(True))
    Catch
        logPath = "(로그 저장 실패)"
    End Try

    ProgFinish(prog)
    Dim msg As String = "처리 : " & nDone & " / " & jobs.Count & "개" & If(stopped, "  (중지함 - 다시 실행하면 이어서 됨)", "") & vbCrLf & _
                        "참조 대체 : " & nRepl & "건,  저장한 파일 : " & nSaved & "개" & vbCrLf & _
                        "실패 : " & nFail & "건" & vbCrLf & _
                        "못 찾은 참조 : " & nLeft & "건  (그중 조립에 쓰이는 파일의 것 " & nLeftUsed & "건)" & vbCrLf & _
                        "   나머지는 조립에 안 쓰이는 옛 파일이 가리키던 것이라 전체 조립도와 무관" & vbCrLf & _
                        "추가로 복사한 파일 : " & GetList(S, "r_extra").Count & "개" & vbCrLf & vbCrLf & _
                        "로그 : " & logPath & vbCrLf & vbCrLf & _
                        "새 위치의 전체 조립도를 열어 링크가 모두 잡히는지 확인하세요." & vbCrLf & _
                        "로그를 지금 열까요?"
    If MessageBox.Show(msg, TTL & " - 완료", MessageBoxButtons.YesNo) = DialogResult.Yes Then OpenWithShell(logPath)
    ProgClose(prog)
End Sub

Function MapRef(S As Dictionary(Of String, Object), oldRef As String, buy As String, _
                Optional jf As String = "", Optional used As String = "?") As String
    Dim dst As String = CStr(S("DST"))
    Dim primary As Dictionary(Of String, String) = CType(S("r_primary"), Dictionary(Of String, String))
    Dim purchKey As Dictionary(Of String, String) = CType(S("r_purchKey"), Dictionary(Of String, String))
    Dim purchAny As Dictionary(Of String, String) = CType(S("r_purchAny"), Dictionary(Of String, String))
    Dim reverse As Dictionary(Of String, String) = CType(S("r_reverse"), Dictionary(Of String, String))

    Dim src As String = ""
    If reverse.ContainsKey(oldRef) Then
        src = reverse(oldRef)
    ElseIf primary.ContainsKey(oldRef) OrElse purchAny.ContainsKey(oldRef) Then
        src = oldRef
    Else
        Dim alt As String = OtherDrive(S, oldRef)
        If alt <> oldRef AndAlso (primary.ContainsKey(alt) OrElse purchAny.ContainsKey(alt)) Then
            src = alt
        Else
            src = BestMatch(S, oldRef)
            If src = "" AndAlso Not IsUnder(oldRef, dst) Then
                If System.IO.File.Exists(oldRef) Then
                    src = oldRef
                ElseIf System.IO.File.Exists(alt) Then
                    src = alt
                End If
            End If
        End If
    End If
    If src = "" Then Return ""

    If primary.ContainsKey(src) Then Return primary(src)

    Dim pinfo() As String = PurchInfo(S, src)
    If pinfo IsNot Nothing Then
        If buy <> "" Then
            Dim key As String = src & "|" & buy
            If purchKey.ContainsKey(key) Then Return purchKey(key)
            Dim made As String = CopyPurchasedNow(S, src, buy, pinfo)
            If made <> "" Then
                purchKey(key) = made
                reverse(made) = src
                Return made
            End If
        End If
        If purchAny.ContainsKey(src) Then Return purchAny(src)
        Return ""
    End If

    If jf <> "" AndAlso System.IO.File.Exists(src) AndAlso Not IsUnder(src, dst) Then
        Dim t As String = System.IO.Path.Combine(System.IO.Path.GetDirectoryName(jf), System.IO.Path.GetFileName(src))
        Dim r As String = CopyFileSafe(src, t)
        If r = "copied" OrElse r = "exists" Then
            If r = "copied" Then
                GetList(S, "r_extra").Add(t)
                QueueRelink(S, t, buy, used)
                For Each de As String In New String() {".idw", ".dwg"}
                    Dim dp As String = System.IO.Path.ChangeExtension(src, de)
                    If System.IO.File.Exists(dp) Then
                        Dim dt As String = System.IO.Path.ChangeExtension(t, de)
                        If CopyFileSafe(dp, dt) = "copied" Then
                            GetList(S, "r_extra").Add(dt)
                            primary(dp) = dt
                            reverse(dt) = dp
                            QueueRelink(S, dt, buy, used)
                        End If
                    End If
                Next
            End If
            primary(src) = t
            reverse(t) = src
            Return t
        End If
    End If
    Return ""
End Function

Function OtherDrive(S As Dictionary(Of String, Object), p As String) As String
    Try
        Dim r1 As String = System.IO.Path.GetPathRoot(p)
        Dim r2 As String = System.IO.Path.GetPathRoot(CStr(S("SRC")))
        If r1 = "" OrElse String.Equals(r1, r2, StringComparison.OrdinalIgnoreCase) Then Return p
        Return r2 & p.Substring(r1.Length)
    Catch
        Return p
    End Try
End Function

Sub QueueRelink(S As Dictionary(Of String, Object), fp As String, buy As String, used As String)
    Dim fe As String = Ext(fp)
    If fe <> ".ipt" AndAlso fe <> ".iam" AndAlso fe <> ".idw" AndAlso fe <> ".dwg" Then Return
    CType(S("r_newJobs"), List(Of String())).Add(New String() {"0", fp, buy, used})
End Sub

Function BestMatch(S As Dictionary(Of String, Object), p As String) As String
    Dim nameIndex As Dictionary(Of String, List(Of String)) = CType(S("r_nameIndex"), Dictionary(Of String, List(Of String)))
    Dim nm As String = System.IO.Path.GetFileName(p)
    If Not nameIndex.ContainsKey(nm) Then Return ""
    Dim cands As List(Of String) = nameIndex(nm)
    If cands.Count = 1 Then Return cands(0)

    Dim ps() As String = p.Split("\"c)
    Dim best As String = ""
    Dim bestN As Integer = -1
    For Each c As String In cands
        Dim cs() As String = c.Split("\"c)
        Dim n As Integer = 0
        Do While n < ps.Length AndAlso n < cs.Length AndAlso _
                 String.Equals(ps(ps.Length - 1 - n), cs(cs.Length - 1 - n), StringComparison.OrdinalIgnoreCase)
            n += 1
        Loop
        If n > bestN Then
            bestN = n
            best = c
        End If
    Next
    Return best
End Function

Function CopyPurchasedNow(S As Dictionary(Of String, Object), src As String, buy As String, pinfo() As String) As String
    If Not System.IO.File.Exists(src) Then Return ""
    Dim extra As List(Of String) = GetList(S, "r_extra")
    If pinfo(0) <> "" Then
        For Each f As String In EnumFiles(S, pinfo(0))
            Dim d2 As String = System.IO.Path.Combine(buy, System.IO.Path.GetFileName(pinfo(0)), f.Substring(pinfo(0).Length + 1))
            If CopyFileSafe(f, d2) = "copied" Then extra.Add(d2)
        Next
    End If
    Dim target As String = System.IO.Path.Combine(buy, pinfo(1))
    Dim r As String = CopyFileSafe(src, target)
    If r = "copied" Then extra.Add(target)
    If r = "copied" AndAlso Ext(target) = ".iam" Then QueueRelink(S, target, buy, "?")
    If System.IO.File.Exists(target) Then Return target
    Return ""
End Function

Function LastDstFile() As String
    Return System.IO.Path.Combine(System.Environment.GetFolderPath(System.Environment.SpecialFolder.ApplicationData), _
                                  "PackAndGoReorganize", "last_dst.txt")
End Function

Function ReadLastDst() As String
    Try
        Dim f As String = LastDstFile()
        If System.IO.File.Exists(f) Then Return System.IO.File.ReadAllText(f, System.Text.Encoding.UTF8).Trim()
    Catch
    End Try
    Return ""
End Function

Sub SaveLastDst(d As String)
    Try
        Dim f As String = LastDstFile()
        System.IO.Directory.CreateDirectory(System.IO.Path.GetDirectoryName(f))
        System.IO.File.WriteAllText(f, d, New System.Text.UTF8Encoding(True))
    Catch
    End Try
End Sub

Function PickFolder(startDir As String, desc As String) As String
    Dim fbd As System.Windows.Forms.FolderBrowserDialog = Nothing
    Try
        fbd = New System.Windows.Forms.FolderBrowserDialog()
        fbd.Description = desc
        fbd.ShowNewFolderButton = True
        If System.IO.Directory.Exists(startDir) Then fbd.SelectedPath = startDir
        If fbd.ShowDialog() = System.Windows.Forms.DialogResult.OK Then Return fbd.SelectedPath
        Return ""
    Catch
    Finally
        If fbd IsNot Nothing Then
            Try
                fbd.Dispose()
            Catch
            End Try
        End If
    End Try

    Dim typed As String = InputBox(desc, "결과 위치", startDir)
    If String.IsNullOrWhiteSpace(typed) Then Return ""
    typed = typed.Trim()
    Try
        System.IO.Directory.CreateDirectory(typed)
    Catch
        MessageBox.Show("폴더를 만들 수 없습니다." & vbCrLf & typed, "결과 위치")
        Return ""
    End Try
    Return typed
End Function

Function ProgOpen(title As String) As System.Windows.Forms.Form
    Dim frm As System.Windows.Forms.Form = Nothing
    Try
        frm = New System.Windows.Forms.Form()
        frm.Text = title
        frm.Width = 760
        frm.Height = 480
        frm.StartPosition = System.Windows.Forms.FormStartPosition.CenterScreen
        frm.FormBorderStyle = System.Windows.Forms.FormBorderStyle.FixedDialog
        frm.MaximizeBox = False
        frm.MinimizeBox = True
        frm.TopMost = True

        Dim lblCount As New System.Windows.Forms.Label
        lblCount.Name = "lblCount"
        lblCount.SetBounds(12, 12, 720, 20)
        lblCount.Text = "준비 중..."

        Dim lblFile As New System.Windows.Forms.Label
        lblFile.Name = "lblFile"
        lblFile.SetBounds(12, 36, 720, 20)
        lblFile.Text = ""

        Dim pb As New System.Windows.Forms.ProgressBar
        pb.Name = "pb"
        pb.SetBounds(12, 62, 720, 22)
        pb.Minimum = 0
        pb.Maximum = 1000

        Dim lblStat As New System.Windows.Forms.Label
        lblStat.Name = "lblStat"
        lblStat.SetBounds(12, 92, 720, 20)
        lblStat.Text = ""

        Dim lst As New System.Windows.Forms.ListBox
        lst.Name = "lst"
        lst.SetBounds(12, 118, 720, 270)
        lst.HorizontalScrollbar = True

        Dim btn As New System.Windows.Forms.Button
        btn.Name = "btn"
        btn.Text = "중지"
        btn.SetBounds(612, 398, 120, 30)
        btn.DialogResult = System.Windows.Forms.DialogResult.Cancel

        frm.Controls.Add(lblCount)
        frm.Controls.Add(lblFile)
        frm.Controls.Add(pb)
        frm.Controls.Add(lblStat)
        frm.Controls.Add(lst)
        frm.Controls.Add(btn)
        frm.Show()
        System.Windows.Forms.Application.DoEvents()
    Catch
        frm = Nothing
    End Try
    Return frm
End Function

Function ProgStopped(frm As System.Windows.Forms.Form) As Boolean
    If frm Is Nothing Then Return False
    Try
        System.Windows.Forms.Application.DoEvents()
        If frm.IsDisposed OrElse Not frm.Visible Then Return True
        Return frm.DialogResult = System.Windows.Forms.DialogResult.Cancel
    Catch
        Return False
    End Try
End Function

Sub ProgSet(frm As System.Windows.Forms.Form, done As Integer, total As Integer, current As String, _
            stats As String, sw As System.Diagnostics.Stopwatch)
    If frm Is Nothing Then Return
    Try
        If frm.IsDisposed Then Return
        Dim pct As Integer = 0
        If total > 0 Then pct = CInt(Math.Floor(done * 1000.0 / total))
        If pct > 1000 Then pct = 1000

        Dim el As Double = sw.Elapsed.TotalSeconds
        Dim remain As String = "계산 중"
        If done > 0 AndAlso total > done Then
            remain = FmtSec(el / done * (total - done))
        ElseIf total > 0 AndAlso done >= total Then
            remain = "0:00"
        End If

        CType(frm.Controls("lblCount"), System.Windows.Forms.Label).Text = _
            done & " / " & total & "   (" & (pct / 10.0).ToString("0.0") & "%)      걸린 시간 " & FmtSec(el) & "   남은 시간 " & remain
        CType(frm.Controls("lblFile"), System.Windows.Forms.Label).Text = "지금 : " & current
        CType(frm.Controls("pb"), System.Windows.Forms.ProgressBar).Value = pct
        CType(frm.Controls("lblStat"), System.Windows.Forms.Label).Text = stats
        System.Windows.Forms.Application.DoEvents()
    Catch
    End Try
End Sub

Sub ProgLine(frm As System.Windows.Forms.Form, txt As String)
    If frm Is Nothing Then Return
    Try
        If frm.IsDisposed Then Return
        Dim lst As System.Windows.Forms.ListBox = CType(frm.Controls("lst"), System.Windows.Forms.ListBox)
        lst.Items.Add(DateTime.Now.ToString("HH:mm:ss") & "   " & txt)
        Do While lst.Items.Count > 500
            lst.Items.RemoveAt(0)
        Loop
        lst.TopIndex = lst.Items.Count - 1
        System.Windows.Forms.Application.DoEvents()
    Catch
    End Try
End Sub

Sub ProgFinish(frm As System.Windows.Forms.Form)
    If frm Is Nothing Then Return
    Try
        If frm.IsDisposed Then Return
        frm.TopMost = False
        CType(frm.Controls("btn"), System.Windows.Forms.Button).Enabled = False
        CType(frm.Controls("btn"), System.Windows.Forms.Button).Text = "끝"
        System.Windows.Forms.Application.DoEvents()
    Catch
    End Try
End Sub

Sub ProgClose(frm As System.Windows.Forms.Form)
    If frm Is Nothing Then Return
    Try
        If Not frm.IsDisposed Then
            frm.Close()
            frm.Dispose()
        End If
    Catch
    End Try
End Sub

Function FmtSec(sec As Double) As String
    If sec < 0 OrElse Double.IsNaN(sec) OrElse Double.IsInfinity(sec) Then Return "-"
    Dim t As Integer = CInt(Math.Round(sec))
    Dim h As Integer = t \ 3600
    Dim m As Integer = (t Mod 3600) \ 60
    Dim ss As Integer = t Mod 60
    If h > 0 Then Return h & ":" & m.ToString("00") & ":" & ss.ToString("00")
    Return m & ":" & ss.ToString("00")
End Function

Sub CloseHiddenDocs()
    For pass As Integer = 1 To 5
        Dim lst As New List(Of Inventor.Document)
        For Each d As Inventor.Document In ThisApplication.Documents
            lst.Add(d)
        Next
        Dim closed As Integer = 0
        For Each d As Inventor.Document In lst
            Try
                If d.Views.Count > 0 Then Continue For
                If d.ReferencingDocuments.Count > 0 Then Continue For
                d.Close(True)
                closed += 1
            Catch
            End Try
        Next
        If closed = 0 Then Exit For
    Next
End Sub
