' ============================================================================
'부품 리비전 일괄 생성(made by pjh)
' ============================================================================

Sub Main()
    Dim SKIP_LETTERS   As String  = ""        ' 리비전에서 제외할 알파벳. 예) "IOQSXZ"
    Dim REPLACE_IN_ASM As Boolean = True      ' 열려있는 조립도에서 구성요소 대치
    Dim MIN_HYPHENS    As Integer = 2         ' 사내 도면번호 판별용 최소 하이픈 수

    Dim FIELD_MOD_TAG  As String  = "(현품수정)"
    Dim ASK_FIELD_MOD  As Boolean = True      ' False=현품수정 선택창을 건너뜀

    Dim SAVE_NEW_FILES As Boolean = True      ' 새 ipt / idw 만 저장 (조립도는 저장 안 함)
    Dim SHOW_NEW_MODEL As Boolean = True      ' 새 모델을 화면에 표시

    Dim drawings As New List(Of Inventor.DrawingDocument)
    Dim models   As New List(Of Inventor.Document)
    Dim names    As New List(Of String)
    Dim newPNs   As New List(Of String)
    Dim noDwg    As New List(Of String)
    Dim existed  As New List(Of String)
    Dim skipped  As New List(Of String)

    Dim selOccs   As New List(Of Inventor.ComponentOccurrence)
    Dim oAct      As Inventor.Document = Nothing
    Dim selOwner  As String = ""
    Dim tgtAsm    As Inventor.AssemblyDocument = Nothing

    Try
        oAct = ThisApplication.ActiveDocument
    Catch
        oAct = Nothing
    End Try

    If oAct IsNot Nothing AndAlso _
       oAct.DocumentType = Inventor.DocumentTypeEnum.kAssemblyDocumentObject Then
        Try
            For Each obj As Object In CType(oAct, Inventor.AssemblyDocument).SelectSet
                Dim occ As Inventor.ComponentOccurrence = TryCast(obj, Inventor.ComponentOccurrence)
                If occ IsNot Nothing Then selOccs.Add(occ)
            Next
        Catch
        End Try

        Try
            selOwner = oAct.FullFileName
        Catch
            selOwner = ""
        End Try

        tgtAsm = CType(oAct, Inventor.AssemblyDocument)
    End If

    Dim useSelection As Boolean = (selOccs.Count > 0)

    Dim candidates As New List(Of Inventor.DrawingDocument)
    Dim seenDwg    As New List(Of String)
    Dim seenMdl    As New List(Of String)

    Dim openedByRule As New List(Of Inventor.DrawingDocument)

    If useSelection Then

        For Each occ As Inventor.ComponentOccurrence In selOccs

            Dim mdlPath As String = ""
            Try
                mdlPath = occ.Definition.Document.FullFileName
            Catch
            End Try
            If String.IsNullOrEmpty(mdlPath) Then Continue For

            If ContainsPath(seenMdl, mdlPath) Then Continue For
            seenMdl.Add(mdlPath)

            Dim dwgPath As String = FindDrawingFor(mdlPath)

            If dwgPath = "" Then
                noDwg.Add(System.IO.Path.GetFileNameWithoutExtension(mdlPath))
                Continue For
            End If

            If ContainsPath(seenDwg, dwgPath) Then Continue For
            seenDwg.Add(dwgPath)

            Dim justOpened As Boolean = False
            Dim opened As Inventor.DrawingDocument = OpenDrawingDoc(dwgPath, justOpened)
            If opened Is Nothing Then
                skipped.Add(System.IO.Path.GetFileName(dwgPath) & "  (도면을 열지 못함)")
                Continue For
            End If

            If justOpened Then openedByRule.Add(opened)
            candidates.Add(opened)

        Next

    Else

        For Each oDoc As Inventor.Document In ThisApplication.Documents
            If oDoc.DocumentType <> Inventor.DocumentTypeEnum.kDrawingDocumentObject Then Continue For
            Try
                If String.IsNullOrEmpty(oDoc.FullFileName) Then Continue For
                If ContainsPath(seenDwg, oDoc.FullFileName) Then Continue For
                seenDwg.Add(oDoc.FullFileName)
                candidates.Add(CType(oDoc, Inventor.DrawingDocument))
            Catch
            End Try
        Next

    End If

    Dim usedMdl As New List(Of String)

    For Each oDrw As Inventor.DrawingDocument In candidates

        Dim dwgName As String = "(이름 없음)"
        Try
            dwgName = System.IO.Path.GetFileName(oDrw.FullFileName)
        Catch
        End Try

        Dim mdl As Inventor.Document = Nothing
        Dim refCnt As Integer = -1
        Try
            refCnt = oDrw.ReferencedDocuments.Count
            If refCnt = 1 Then mdl = oDrw.ReferencedDocuments.Item(1)
        Catch
        End Try

        If mdl Is Nothing Then
            If refCnt >= 0 Then
                skipped.Add(dwgName & "  (참조 모델이 " & refCnt & "개 - 1개인 도면만 처리)")
            Else
                skipped.Add(dwgName & "  (참조를 읽지 못함)")
            End If
            Continue For
        End If

        Dim curPN As String = ReadPN(mdl)
        If String.IsNullOrWhiteSpace(curPN) Then
            skipped.Add(dwgName & "  (부품번호를 읽지 못함)")
            Continue For
        End If

        If ContainsPath(usedMdl, mdl.FullFileName) Then
            skipped.Add(dwgName & "  (같은 모델을 가리키는 도면이 이미 목록에 있음)")
            Continue For
        End If
        usedMdl.Add(mdl.FullFileName)

        Dim hy As Integer = 0
        For Each ch As Char In curPN
            If ch = "-"c Then hy += 1
        Next
        If hy < MIN_HYPHENS Then
            skipped.Add(curPN & "  (하이픈 " & hy & "개 - 사내 도면번호 형식 아님)")
            Continue For
        End If

        Dim nextPN As String = BumpPartNumber(curPN, SKIP_LETTERS)
        If nextPN = "" Then
            skipped.Add(curPN & "  (리비전 문자를 해석하지 못함)")
            Continue For
        End If

        Dim mDir As String = System.IO.Path.GetDirectoryName(mdl.FullFileName)
        Dim dDir As String = System.IO.Path.GetDirectoryName(oDrw.FullFileName)
        Dim mExt As String = System.IO.Path.GetExtension(mdl.FullFileName)
        Dim dExt As String = System.IO.Path.GetExtension(oDrw.FullFileName)

        Dim lastRev As String = LatestExistingRev(curPN, SKIP_LETTERS, _
                                                  mDir, mExt, dDir, dExt)

        If lastRev <> "" Then
            Dim adv As String = BumpPartNumber(lastRev, SKIP_LETTERS)
            If adv = "" Then
                skipped.Add(curPN & "  (" & lastRev & " 의 다음 리비전을 계산하지 못함)")
                Continue For
            End If
            nextPN = adv
        End If

        drawings.Add(oDrw)
        models.Add(mdl)
        newPNs.Add(nextPN)
        existed.Add(lastRev)

        If lastRev = "" Then
            names.Add(curPN & "   →   " & nextPN)
        Else
            names.Add(curPN & "   →   " & nextPN & "   (" & lastRev & " 이미 있음)")
        End If

    Next

    If drawings.Count = 0 Then
        Dim nm As String = "대상 도면이 없습니다." & vbCrLf & vbCrLf & _
                           "조건 : 저장된 도면 / 참조 모델 1개 / 사내 도면번호 형식"
        If noDwg.Count > 0 Then
            nm &= vbCrLf & vbCrLf & "[도면 파일을 찾지 못함]" & vbCrLf & _
                  String.Join(vbCrLf, noDwg.ToArray()) & vbCrLf & _
                  "(모델과 같은 폴더에 같은 이름의 .idw / .dwg 가 있어야 합니다)"
        End If
        If skipped.Count > 0 Then
            nm &= vbCrLf & vbCrLf & "[그 밖의 제외 사유]" & vbCrLf & _
                  String.Join(vbCrLf, skipped.ToArray())
        End If
        CloseOpenedDrawings(openedByRule)
        MessageBox.Show(nm, "리비전 생성")
        Return
    End If

    Dim pickMsg As String = "리비전을 딸 도면을 선택하세요."
    If noDwg.Count > 0 Then
        pickMsg &= "   (도면을 못 찾은 " & noDwg.Count & "건 제외)"
    End If
    If skipped.Count > 0 Then
        pickMsg &= "   (조건 불일치 " & skipped.Count & "건 제외)"
    End If

    Dim picked As List(Of Integer) = Nothing

    If useSelection Then

        picked = New List(Of Integer)
        For i As Integer = 0 To names.Count - 1
            picked.Add(i)
        Next

    Else

        picked = PickList(names, pickMsg, True)
        If picked Is Nothing Then
            CloseOpenedDrawings(openedByRule)
            Return
        End If

    End If

    If picked.Count = 0 Then
        CloseOpenedDrawings(openedByRule)
        MessageBox.Show("선택된 도면이 없습니다.", "리비전 생성")
        Return
    End If

    Dim confirmed As New List(Of Integer)

    For Each ix As Integer In picked

        If existed(ix) = "" Then
            confirmed.Add(ix)
            Continue For
        End If

        Dim srcPN As String = ReadPN(models(ix))

        Dim q1 As System.Windows.Forms.DialogResult = MessageBox.Show( _
            srcPN & " 의 다음 리비전이 이미 있습니다." & vbCrLf & vbCrLf & _
            "   이미 있는 최신 리비전 : " & existed(ix) & vbCrLf & _
            "   새로 만들 리비전       : " & newPNs(ix) & vbCrLf & vbCrLf & _
            "새 리비전은 지금 고른 " & srcPN & " 에서 복사합니다." & vbCrLf & _
            existed(ix) & " 에서 바뀐 내용은 반영되지 않습니다." & vbCrLf & vbCrLf & _
            "[예]     " & newPNs(ix) & " 로 새로 만듭니다" & vbCrLf & _
            "[아니오]  이 부품은 건너뜁니다" & vbCrLf & _
            "[취소]   규칙 실행을 취소합니다", _
            "리비전 생성 - 이미 있는 리비전", MessageBoxButtons.YesNoCancel)

        If q1 = DialogResult.Yes Then
            confirmed.Add(ix)

        ElseIf q1 = DialogResult.Cancel Then
            CloseOpenedDrawings(openedByRule)
            MessageBox.Show("규칙 실행을 취소했습니다." & vbCrLf & _
                            "만들어진 파일은 없습니다.", "리비전 생성")
            Return
        End If

    Next

    picked = confirmed

    If picked.Count = 0 Then
        CloseOpenedDrawings(openedByRule)
        MessageBox.Show("처리할 부품이 없습니다." & vbCrLf & _
                        "이미 리비전이 있는 부품을 모두 건너뛰었습니다.", "리비전 생성")
        Return
    End If

    Dim asmPlan As New List(Of Integer)

    For Each ix As Integer In picked

        Dim mode As Integer = 0

        If REPLACE_IN_ASM AndAlso useSelection Then

            Dim oldP As String = models(ix).FullFileName
            Dim total As Integer = 0
            Dim mine  As Integer = 0
            Dim asmNm As String = ""
            Dim pnm   As String = System.IO.Path.GetFileNameWithoutExtension(oldP)

            asmNm = System.IO.Path.GetFileName(selOwner)
            CountInAssembly(tgtAsm, oldP, selOccs, selOwner, total, mine)

            If total > 1 AndAlso mine > 0 AndAlso mine < total Then

                Dim q2 As System.Windows.Forms.DialogResult = MessageBox.Show( _
                    pnm & " 부품이" & vbCrLf & _
                    "조립도 [" & asmNm & "] 에 " & total & "개 배치되어 있고," & vbCrLf & _
                    "그중 " & mine & "개를 선택하셨습니다." & vbCrLf & vbCrLf & _
                    "[예]     선택한 " & mine & "개만 대치" & vbCrLf & _
                    "[아니오]  이 조립도 안의 " & total & "개 전부 대치" & vbCrLf & _
                    "[취소]   규칙 실행을 취소합니다 (파일도 만들지 않음)", _
                    "조립도 대치 범위", MessageBoxButtons.YesNoCancel)

                If q2 = DialogResult.Yes Then
                    mode = 1
                ElseIf q2 = DialogResult.No Then
                    mode = 0
                Else
                    CloseOpenedDrawings(openedByRule)
                    MessageBox.Show("규칙 실행을 취소했습니다." & vbCrLf & _
                                    "만들어진 파일은 없습니다.", "리비전 생성")
                    Return
                End If

            ElseIf total > 1 AndAlso mine = 0 Then

                Dim q3 As System.Windows.Forms.DialogResult = MessageBox.Show( _
                    pnm & " 부품이" & vbCrLf & _
                    "조립도 [" & asmNm & "] 에 " & total & "개 배치되어 있습니다." & vbCrLf & _
                    "선택하신 것이 그중 어느 배치인지는 특정하지 못했습니다." & vbCrLf & vbCrLf & _
                    "[예]     이 조립도 안의 " & total & "개 전부 대치" & vbCrLf & _
                    "[아니오]  조립도는 그대로 두고 파일만 생성" & vbCrLf & _
                    "[취소]   규칙 실행을 취소합니다 (파일도 만들지 않음)", _
                    "조립도 대치 범위", MessageBoxButtons.YesNoCancel)

                If q3 = DialogResult.Yes Then
                    mode = 0
                ElseIf q3 = DialogResult.No Then
                    mode = 2
                Else
                    CloseOpenedDrawings(openedByRule)
                    MessageBox.Show("규칙 실행을 취소했습니다." & vbCrLf & _
                                    "만들어진 파일은 없습니다.", "리비전 생성")
                    Return
                End If

            End If
        End If

        asmPlan.Add(mode)
    Next

    Dim isFieldMod As New List(Of Boolean)

    For Each ix As Integer In picked
        Dim d0 As String = ReadProp(models(ix), "Description")
        isFieldMod.Add(d0.IndexOf(FIELD_MOD_TAG, StringComparison.Ordinal) >= 0)
    Next

    If ASK_FIELD_MOD Then

        Dim subNames As New List(Of String)
        Dim preChk   As New List(Of Boolean)
        Dim already2 As Integer = 0

        Dim si As Integer = 0
        For Each ix As Integer In picked

            Dim dsc As String = ReadProp(models(ix), "Description")
            Dim hasTag As Boolean = isFieldMod(si)

            Dim lbl2 As String = ReadPN(models(ix)) & "   [" & dsc & "]"
            If hasTag Then
                lbl2 &= "   ← 현재 붙어있음"
                already2 += 1
            End If

            subNames.Add(lbl2)
            preChk.Add(hasTag)
            si += 1
        Next

        Dim msg2 As String = "현품수정 항목을 확인하세요. 체크된 항목의 설명에 " & _
                             FIELD_MOD_TAG & " 가 붙습니다."
        If already2 > 0 Then
            msg2 &= "   (이미 붙어있는 " & already2 & "건은 체크된 상태입니다. 해제하면 제거됩니다)"
        End If

        Dim picked2 As List(Of Integer) = PickListPre(subNames, msg2, preChk)

        If picked2 Is Nothing Then
            CloseOpenedDrawings(openedByRule)
            Return
        End If

        For i2 As Integer = 0 To isFieldMod.Count - 1
            isFieldMod(i2) = False
        Next
        For Each k As Integer In picked2
            isFieldMod(k) = True
        Next
    End If

    Dim curPNs   As New List(Of String)
    Dim editPNs  As New List(Of String)
    Dim mdlPaths As New List(Of String)
    Dim drwPaths As New List(Of String)

    For Each ix As Integer In picked
        curPNs.Add(ReadPN(models(ix)))
        editPNs.Add(newPNs(ix))
        mdlPaths.Add(models(ix).FullFileName)
        drwPaths.Add(drawings(ix).FullFileName)
    Next

    If Not EditPartNumbers(curPNs, mdlPaths, drwPaths, editPNs) Then
        CloseOpenedDrawings(openedByRule)
        Return
    End If

    Dim ep As Integer = 0
    For Each ix As Integer In picked
        newPNs(ix) = editPNs(ep)
        ep += 1
    Next

    Dim conflicts  As New List(Of String)
    Dim newIptList As New List(Of String)
    Dim newIdwList As New List(Of String)
    Dim oldIptList As New List(Of String)
    Dim oldPNList  As New List(Of String)

    For Each ix As Integer In picked

        Dim mdlPath As String = models(ix).FullFileName
        Dim drwPath As String = drawings(ix).FullFileName

        Dim mdlDir  As String = System.IO.Path.GetDirectoryName(mdlPath)
        Dim drwDir  As String = System.IO.Path.GetDirectoryName(drwPath)
        Dim mdlExt  As String = System.IO.Path.GetExtension(mdlPath)
        Dim drwExt  As String = System.IO.Path.GetExtension(drwPath)

        Dim newIpt As String = System.IO.Path.Combine(mdlDir, newPNs(ix) & mdlExt)
        Dim newIdw As String = System.IO.Path.Combine(drwDir, newPNs(ix) & drwExt)

        newIptList.Add(newIpt)
        newIdwList.Add(newIdw)

        oldIptList.Add(mdlPath)
        oldPNList.Add(ReadPN(models(ix)))

        If System.IO.File.Exists(newIpt) Then conflicts.Add(System.IO.Path.GetFileName(newIpt))
        If System.IO.File.Exists(newIdw) Then conflicts.Add(System.IO.Path.GetFileName(newIdw))

    Next

    If conflicts.Count > 0 Then
        CloseOpenedDrawings(openedByRule)
        MessageBox.Show("같은 이름의 파일이 이미 있습니다. 중단합니다." & vbCrLf & _
                        "(덮어쓰지 않습니다)" & vbCrLf & vbCrLf & _
                        String.Join(vbCrLf, conflicts.ToArray()), "리비전 생성 - 중단")
        Return
    End If

    Dim logTxt As String = ""
    Dim okCount As Integer = 0
    Dim orphan As New List(Of String)
    Dim prevSilent As Boolean = ThisApplication.SilentOperation

    Try
        ThisApplication.SilentOperation = True

        Dim n As Integer = 0
        For Each ix As Integer In picked

            n += 1
            Dim oldPN  As String = oldPNList(n - 1)
            Dim newPN  As String = newPNs(ix)
            Dim newIpt As String = newIptList(n - 1)
            Dim newIdw As String = newIdwList(n - 1)
            Dim oldIpt As String = oldIptList(n - 1)

            logTxt &= vbCrLf & "━━ " & oldPN & " → " & newPN & " ━━" & vbCrLf

            Dim newModel As Inventor.Document = Nothing
            Dim newDrw   As Inventor.DrawingDocument = Nothing

            Try
                models(ix).SaveAs(newIpt, True)
                logTxt &= "  1) 모델 사본 : 성공" & vbCrLf
            Catch ex As Exception
                logTxt &= "  1) 모델 사본 : 실패 → " & ex.Message & vbCrLf
                logTxt &= Hint(ex.Message)
                Continue For
            End Try

            Try
                newModel = ThisApplication.Documents.Open(newIpt, SHOW_NEW_MODEL)
                WritePN(newModel, newPN)
                logTxt &= "  2) 부품번호 수정 : 성공" & vbCrLf

                Dim oldD As String = ReadProp(newModel, "Description")
                Dim newD As String = ApplyTag(oldD, FIELD_MOD_TAG, isFieldMod(n - 1))

                If newD = oldD Then
                    If isFieldMod(n - 1) Then
                        logTxt &= "  2-1) 현품수정 표기 : 이미 있음 (변경 없음)" & vbCrLf
                    End If
                Else
                    WriteProp(newModel, "Description", newD)
                    If isFieldMod(n - 1) Then
                        logTxt &= "  2-1) 현품수정 표기 추가 : " & oldD & " → " & newD & vbCrLf
                    Else
                        logTxt &= "  2-1) 현품수정 표기 제거 : " & oldD & " → " & newD & vbCrLf
                    End If
                End If

            Catch ex As Exception
                logTxt &= "  2) 부품번호 수정 : 실패 → " & ex.Message & vbCrLf
                TryCloseDoc(newModel)
                orphan.Add(System.IO.Path.GetFileName(newIpt))
                Continue For
            End Try

            Try
                drawings(ix).SaveAs(newIdw, True)
                logTxt &= "  3) 도면 사본 : 성공" & vbCrLf
            Catch ex As Exception
                logTxt &= "  3) 도면 사본 : 실패 → " & ex.Message & vbCrLf
                logTxt &= Hint(ex.Message)
                TryCloseDoc(newModel)
                orphan.Add(System.IO.Path.GetFileName(newIpt))
                Continue For
            End Try

            Try
                newDrw = CType(ThisApplication.Documents.Open(newIdw, True), Inventor.DrawingDocument)

                Dim fds As New List(Of Inventor.FileDescriptor)
                For Each fd As Inventor.FileDescriptor In newDrw.File.ReferencedFileDescriptors
                    fds.Add(fd)
                Next

                Dim replaced As Integer = 0
                For Each fd As Inventor.FileDescriptor In fds
                    Try
                        If String.Equals(fd.FullFileName, oldIpt, StringComparison.OrdinalIgnoreCase) Then
                            fd.ReplaceReference(newIpt)
                            replaced += 1
                        End If
                    Catch
                    End Try
                Next

                If replaced = 0 Then
                    Dim oldBase As String = System.IO.Path.GetFileName(oldIpt)
                    For Each fd As Inventor.FileDescriptor In fds
                        Try
                            Dim fb As String = System.IO.Path.GetFileName(fd.FullFileName)
                            If String.Equals(fb, oldBase, StringComparison.OrdinalIgnoreCase) AndAlso _
                               Not String.Equals(fd.FullFileName, newIpt, StringComparison.OrdinalIgnoreCase) Then
                                fd.ReplaceReference(newIpt)
                                replaced += 1
                            End If
                        Catch
                        End Try
                    Next
                    If replaced > 0 Then
                        logTxt &= "  4) 참조 대체 : 경로 표기가 달라 파일명으로 찾아 대체함" & vbCrLf
                    End If
                End If

                If replaced = 0 Then
                    logTxt &= "  4) 참조 대체 : ★ 대상 없음 - 도면이 어느 모델을 보는지 직접 확인하세요" & vbCrLf
                Else
                    logTxt &= "  4) 참조 대체 : 성공 (" & replaced & "건)" & vbCrLf
                End If

                newDrw.Update()

            Catch ex As Exception
                logTxt &= "  4) 참조 대체 : 실패 → " & ex.Message & vbCrLf
                TryCloseDoc(newDrw)
                TryCloseDoc(newModel)
                orphan.Add(System.IO.Path.GetFileName(newIpt))
                orphan.Add(System.IO.Path.GetFileName(newIdw))
                Continue For
            End Try

            Try
                Dim cur As String = ReadPN(newModel)
                Dim restored As Boolean = False
                Try
                    WritePN(newModel, cur & "#")
                    WritePN(newModel, cur)
                    restored = True
                Finally
                    If Not restored Then
                        Try
                            WritePN(newModel, cur)
                        Catch
                        End Try
                    End If
                End Try

                If String.Equals(ReadPN(newModel), cur, StringComparison.Ordinal) Then
                    newDrw.Update()
                    logTxt &= "  5) 타이틀블록 갱신 : 성공" & vbCrLf
                Else
                    logTxt &= "  5) 타이틀블록 갱신 : ★ 부품번호 복원 실패 - 직접 확인 필요" & vbCrLf
                End If

            Catch ex As Exception
                logTxt &= "  5) 타이틀블록 갱신 : 실패 → " & ex.Message & vbCrLf
            End Try

            If SAVE_NEW_FILES Then
                Dim savedM As Boolean = False
                Try
                    newModel.Save()
                    savedM = True
                Catch ex As Exception
                    logTxt &= "  6) 모델 저장 : 실패 → " & ex.Message & vbCrLf
                    logTxt &= Hint(ex.Message)
                End Try

                Try
                    newDrw.Save()
                    If savedM Then
                        logTxt &= "  6) 새 파일 저장 : 성공 (모델 + 도면)" & vbCrLf
                    Else
                        logTxt &= "  6) 도면 저장 : 성공 (모델은 실패 - 부품번호 미반영 상태)" & vbCrLf
                    End If
                Catch ex As Exception
                    logTxt &= "  6) 도면 저장 : 실패 → " & ex.Message & vbCrLf
                    logTxt &= Hint(ex.Message)
                End Try
            Else
                logTxt &= "  6) 새 파일 저장 : 건너뜀 (설정) - ★ 직접 저장해야 부품번호가 반영됩니다" & vbCrLf
            End If

            If REPLACE_IN_ASM Then

                If tgtAsm Is Nothing Then
                    logTxt &= "  7) 조립도 대치 : 건너뜀 (조립도에서 실행하지 않음)" & vbCrLf
                ElseIf asmPlan(n - 1) = 2 Then
                    logTxt &= "  7) 조립도 대치 : 건너뜀 (사용자 선택)" & vbCrLf
                Else
                    Dim onlySel As Boolean = (asmPlan(n - 1) = 1)
                    Dim failCnt As Integer = 0
                    Dim asmHit As Integer = ReplaceInAssembly(tgtAsm, oldIpt, newIpt, selOccs, selOwner, _
                                                              onlySel, failCnt)

                    If asmHit < 0 Then
                        logTxt &= "  7) 조립도 대치 : 오류 발생" & vbCrLf
                    ElseIf asmHit = 0 Then
                        logTxt &= "  7) 조립도 대치 : 대상 없음 (이 조립도에 해당 부품이 없음)" & vbCrLf
                    ElseIf onlySel Then
                        logTxt &= "  7) 조립도 대치 : 선택한 " & asmHit & "개만 대치" & vbCrLf
                    Else
                        logTxt &= "  7) 조립도 대치 : 이 조립도 안의 " & asmHit & "개 전부 대치" & vbCrLf
                    End If
                    If failCnt > 0 Then
                        logTxt &= "     ┗ ★ " & failCnt & "개는 대치하지 못함 - 직접 확인하세요" & vbCrLf
                    End If
                End If
            End If

            okCount += 1

        Next

    Catch ex As Exception
        logTxt &= vbCrLf & "★ 전체 처리 오류 : " & ex.Message & vbCrLf

    Finally
        ThisApplication.SilentOperation = prevSilent
    End Try

    Dim msg As String = "리비전 생성 완료  (" & okCount & " / " & picked.Count & "건)" & vbCrLf & logTxt

    If orphan.Count > 0 Then
        msg &= vbCrLf & "[중간에 실패해 디스크에 남은 파일]" & vbCrLf & _
               String.Join(vbCrLf, orphan.ToArray()) & vbCrLf & _
               "다시 실행하기 전에 지우거나 확인하세요." & vbCrLf
    End If

    If SAVE_NEW_FILES Then
        msg &= vbCrLf & "※ 새 파일은 저장되었습니다. 조립도는 저장하지 않았습니다." & vbCrLf & _
               "   조립도를 확인한 뒤 저장하세요."
    Else
        msg &= vbCrLf & "※ 아직 저장되지 않았습니다." & vbCrLf & _
               "   도면번호와 조립도를 확인한 뒤 저장하세요."
    End If

    MessageBox.Show(msg, "리비전 생성")
End Sub

Sub CountInAssembly(oAsm As Inventor.AssemblyDocument, oldPath As String, _
                    selOccs As List(Of Inventor.ComponentOccurrence), _
                    asmPath As String, _
                    ByRef total As Integer, ByRef mine As Integer)

    total = 0
    mine = 0

    Try
        For Each occ As Inventor.ComponentOccurrence In oAsm.ComponentDefinition.Occurrences
            Try
                If String.Equals(occ.Definition.Document.FullFileName, oldPath, _
                                 StringComparison.OrdinalIgnoreCase) Then
                    total += 1
                    If IsSelected(occ, selOccs, asmPath, asmPath) Then mine += 1
                End If
            Catch
            End Try
        Next
    Catch
    End Try

End Sub

Function ReplaceInAssembly(oAsm As Inventor.AssemblyDocument, _
                           oldPath As String, newPath As String, _
                           selOccs As List(Of Inventor.ComponentOccurrence), _
                           asmPath As String, onlySelected As Boolean, _
                           ByRef failCnt As Integer) As Integer

    failCnt = 0

    Dim victims As New List(Of Inventor.ComponentOccurrence)

    Try
        For Each occ As Inventor.ComponentOccurrence In oAsm.ComponentDefinition.Occurrences
            Try
                If String.Equals(occ.Definition.Document.FullFileName, oldPath, _
                                 StringComparison.OrdinalIgnoreCase) Then
                    If (Not onlySelected) OrElse IsSelected(occ, selOccs, asmPath, asmPath) Then
                        victims.Add(occ)
                    End If
                End If
            Catch
            End Try
        Next
    Catch
        Return -1
    End Try

    Dim done As Integer = 0

    For Each v As Inventor.ComponentOccurrence In victims
        Try
            v.Replace(newPath, False)
            done += 1
        Catch
            failCnt += 1
        End Try
    Next

    Return done

End Function

Function IsSelected(v As Inventor.ComponentOccurrence, _
                    selOccs As List(Of Inventor.ComponentOccurrence), _
                    asmPath As String, selOwner As String) As Boolean
    If selOccs Is Nothing OrElse selOccs.Count = 0 Then Return False

    For Each sel As Inventor.ComponentOccurrence In selOccs
        Try
            If v Is sel Then Return True
        Catch
        End Try
    Next

    If selOwner <> "" AndAlso asmPath <> "" AndAlso _
       Not String.Equals(asmPath, selOwner, StringComparison.OrdinalIgnoreCase) Then
        Return False
    End If

    Dim vn As String = ""
    Try
        vn = v.Name
    Catch
        Return False
    End Try
    If vn = "" Then Return False

    For Each sel As Inventor.ComponentOccurrence In selOccs
        Try
            If String.Equals(vn, sel.Name, StringComparison.Ordinal) Then Return True
        Catch
        End Try
    Next

    Return False
End Function

Function ReadPN(d As Inventor.Document) As String
    Try
        Return CStr(d.PropertySets.Item("Design Tracking Properties").Item("Part Number").Value)
    Catch
        Return ""
    End Try
End Function

Sub WritePN(d As Inventor.Document, v As String)
    d.PropertySets.Item("Design Tracking Properties").Item("Part Number").Value = v
End Sub

Function ContainsPath(list As List(Of String), p As String) As Boolean
    If list Is Nothing OrElse String.IsNullOrEmpty(p) Then Return False
    For Each s As String In list
        If String.Equals(s, p, StringComparison.OrdinalIgnoreCase) Then Return True
    Next
    Return False
End Function

Sub CloseOpenedDrawings(opened As List(Of Inventor.DrawingDocument))
    If opened Is Nothing Then Return

    For Each d As Inventor.DrawingDocument In opened
        Try
            d.Close(True)
        Catch
        End Try
    Next

    opened.Clear()
End Sub

Sub SetDefaultButtons(frm As System.Windows.Forms.Form, _
                      okBtn As System.Windows.Forms.Button, _
                      cancelBtn As System.Windows.Forms.Button)
    Try
        frm.GetType().GetProperty("AcceptButton").SetValue(frm, okBtn)
    Catch
    End Try

    Try
        frm.GetType().GetProperty("CancelButton").SetValue(frm, cancelBtn)
    Catch
    End Try
End Sub

Sub TryCloseDoc(d As Inventor.Document)
    If d Is Nothing Then Return
    Try
        d.Close(True)
    Catch
    End Try
End Sub

Function FindDrawingFor(modelPath As String) As String
    Try
        Dim dir  As String = System.IO.Path.GetDirectoryName(modelPath)
        Dim base As String = System.IO.Path.GetFileNameWithoutExtension(modelPath)

        Dim c1 As String = System.IO.Path.Combine(dir, base & ".idw")
        If System.IO.File.Exists(c1) Then Return c1

        Dim c2 As String = System.IO.Path.Combine(dir, base & ".dwg")
        If System.IO.File.Exists(c2) Then Return c2
    Catch
    End Try

    Return ""
End Function

Function OpenDrawingDoc(dwgPath As String, ByRef justOpened As Boolean) As Inventor.DrawingDocument
    justOpened = False

    Try
        For Each oDoc As Inventor.Document In ThisApplication.Documents
            If oDoc.DocumentType <> Inventor.DocumentTypeEnum.kDrawingDocumentObject Then Continue For
            Try
                If String.Equals(oDoc.FullFileName, dwgPath, StringComparison.OrdinalIgnoreCase) Then
                    Return CType(oDoc, Inventor.DrawingDocument)
                End If
            Catch
            End Try
        Next
    Catch
    End Try

    Try
        Dim d As Inventor.DrawingDocument = _
            CType(ThisApplication.Documents.Open(dwgPath, True), Inventor.DrawingDocument)
        justOpened = True
        Return d
    Catch
        Return Nothing
    End Try
End Function

Function Hint(errMsg As String) As String
    If errMsg Is Nothing Then Return ""

    If errMsg.IndexOf("0x80070057", StringComparison.OrdinalIgnoreCase) >= 0 _
       OrElse errMsg.IndexOf("E_INVALIDARG", StringComparison.OrdinalIgnoreCase) >= 0 _
       OrElse errMsg.IndexOf("매개 변수가 틀립니다", StringComparison.Ordinal) >= 0 Then

        Return "     ┗ 대처 : 캐시 정리 규칙을 실행한 뒤 다시 시도하세요." & vbCrLf & _
               "            이전에 만든 파일을 탐색기에서 지웠을 때 자주 발생합니다." & vbCrLf & _
               "            파일을 지워도 인벤터는 그 문서를 메모리에 계속 들고 있어" & vbCrLf & _
               "            같은 이름과 부딪힙니다. 인벤터를 껐다 켤 필요는 없습니다." & vbCrLf
    End If

    If errMsg.IndexOf("0x80070005", StringComparison.OrdinalIgnoreCase) >= 0 _
       OrElse errMsg.IndexOf("액세스", StringComparison.Ordinal) >= 0 _
       OrElse errMsg.IndexOf("denied", StringComparison.OrdinalIgnoreCase) >= 0 Then

        Return "     ┗ 대처 : 파일이 읽기 전용이거나 권한이 없습니다." & vbCrLf & _
               "            Vault 체크아웃 상태와 폴더 쓰기 권한을 확인하세요." & vbCrLf
    End If

    If errMsg.IndexOf("0x80070020", StringComparison.OrdinalIgnoreCase) >= 0 _
       OrElse errMsg.IndexOf("사용 중", StringComparison.Ordinal) >= 0 Then

        Return "     ┗ 대처 : 다른 프로그램이 파일을 사용 중입니다." & vbCrLf & _
               "            해당 파일을 쓰는 프로그램을 닫고 다시 시도하세요." & vbCrLf
    End If

    Return ""
End Function

Function ReadProp(d As Inventor.Document, pname As String) As String
    Try
        Return CStr(d.PropertySets.Item("Design Tracking Properties").Item(pname).Value)
    Catch
        Return ""
    End Try
End Function

Sub WriteProp(d As Inventor.Document, pname As String, v As String)
    d.PropertySets.Item("Design Tracking Properties").Item(pname).Value = v
End Sub

Function ApplyTag(src As String, tag As String, want As Boolean) As String
    If src Is Nothing Then src = ""
    If String.IsNullOrEmpty(tag) Then Return src

    If want Then
        If src.IndexOf(tag, StringComparison.Ordinal) >= 0 Then Return src
        Return src.TrimEnd() & tag
    End If

    Dim res As String = src
    Do While res.IndexOf(tag, StringComparison.Ordinal) >= 0
        res = res.Replace(tag, "")
    Loop

    Do While res.IndexOf("  ", StringComparison.Ordinal) >= 0
        res = res.Replace("  ", " ")
    Loop

    Return res.Trim()
End Function

Function LatestExistingRev(curPN As String, skipLetters As String, _
                           mDir As String, mExt As String, _
                           dDir As String, dExt As String) As String
    Dim GAP  As Integer = 3
    Dim SCAN As Integer = 60

    Dim last  As String = ""
    Dim probe As String = curPN
    Dim miss  As Integer = 0

    For n As Integer = 1 To SCAN

        Dim nxt As String = BumpPartNumber(probe, skipLetters)
        If nxt = "" Then Exit For

        Dim hit As Boolean = False
        Try
            If System.IO.File.Exists(System.IO.Path.Combine(mDir, nxt & mExt)) Then
                hit = True
            ElseIf System.IO.File.Exists(System.IO.Path.Combine(dDir, nxt & dExt)) Then
                hit = True
            End If
        Catch
        End Try

        If hit Then
            last = nxt
            miss = 0
        Else
            miss += 1
            If miss >= GAP Then Exit For
        End If

        probe = nxt
    Next

    Return last
End Function

Function BumpPartNumber(pn As String, skipLetters As String) As String
    If String.IsNullOrWhiteSpace(pn) Then Return ""

    Dim s As String = pn.Trim()

    Dim i As Integer = s.Length - 1
    While i >= 0 AndAlso Char.IsUpper(s.Chars(i))
        i -= 1
    End While

    Dim baseStr As String = s.Substring(0, i + 1)
    Dim rev     As String = s.Substring(i + 1)

    If baseStr.Length = 0 Then Return ""
    If Not Char.IsDigit(baseStr.Chars(baseStr.Length - 1)) Then Return ""

    Dim nr As String = NextRev(rev, skipLetters)
    If nr = "" Then Return ""

    Return baseStr & nr
End Function

Function NextRev(rev As String, skipLetters As String) As String
    If skipLetters Is Nothing Then skipLetters = ""

    Dim allowed As String = ""
    For c As Integer = Asc("A") To Asc("Z")
        If skipLetters.IndexOf(Chr(c)) < 0 Then allowed &= Chr(c)
    Next
    If allowed.Length = 0 Then allowed = "ABCDEFGHIJKLMNOPQRSTUVWXYZ"

    If String.IsNullOrEmpty(rev) Then Return allowed.Substring(0, 1)

    Dim idxList As New List(Of Integer)
    For Each ch As Char In rev
        Dim k As Integer = allowed.IndexOf(ch)
        If k < 0 Then Return ""
        idxList.Add(k)
    Next

    Dim p As Integer = idxList.Count - 1
    Do
        idxList(p) = idxList(p) + 1
        If idxList(p) < allowed.Length Then Exit Do
        idxList(p) = 0
        p -= 1
        If p < 0 Then
            idxList.Insert(0, 0)
            Exit Do
        End If
    Loop

    Dim res As String = ""
    For Each k As Integer In idxList
        res &= allowed.Substring(k, 1)
    Next

    Return res
End Function

Function PickList(names As List(Of String), prompt As String, _
                  defaultChecked As Boolean) As List(Of Integer)
    Dim frm As New System.Windows.Forms.Form
    Dim picked As List(Of Integer) = Nothing

    Try
        frm.Text = "리비전 생성"
        frm.Width  = 576
        frm.Height = 480
        frm.StartPosition = System.Windows.Forms.FormStartPosition.CenterScreen
        frm.FormBorderStyle = System.Windows.Forms.FormBorderStyle.FixedDialog
        frm.MinimizeBox = False
        frm.MaximizeBox = False
        frm.TopMost = True

        Dim lbl As New System.Windows.Forms.Label
        lbl.Text = prompt
        lbl.SetBounds(12, 12, 536, 20)

        Dim clb As New System.Windows.Forms.CheckedListBox
        clb.SetBounds(12, 38, 536, 340)
        clb.CheckOnClick = True

        For Each nm As String In names
            clb.Items.Add(nm, defaultChecked)
        Next


        Dim btnOK As New System.Windows.Forms.Button
        btnOK.Text = "확인"
        btnOK.SetBounds(352, 392, 92, 32)
        btnOK.DialogResult = System.Windows.Forms.DialogResult.OK

        Dim btnCancel As New System.Windows.Forms.Button
        btnCancel.Text = "취소"
        btnCancel.SetBounds(456, 392, 92, 32)
        btnCancel.DialogResult = System.Windows.Forms.DialogResult.Cancel

        frm.Controls.Add(lbl)
        frm.Controls.Add(clb)
        frm.Controls.Add(btnOK)
        frm.Controls.Add(btnCancel)
        SetDefaultButtons(frm, btnOK, btnCancel)

        Dim result As System.Windows.Forms.DialogResult = frm.ShowDialog()

        If result = System.Windows.Forms.DialogResult.OK Then
            picked = New List(Of Integer)
            For Each ix As Integer In clb.CheckedIndices
                picked.Add(ix)
            Next
        End If

    Finally
        frm.Dispose()
    End Try

    Return picked
End Function

Function EditPartNumbers(curPNs As List(Of String), _
                         mdlPaths As List(Of String), _
                         drwPaths As List(Of String), _
                         ByRef editPNs As List(Of String)) As Boolean
    Dim n As Integer = curPNs.Count

    Dim autoPNs As New List(Of String)
    For i As Integer = 0 To n - 1
        autoPNs.Add(editPNs(i))
    Next

    Dim rowH As Integer = 30
    Dim listH As Integer = n * rowH
    If listH > 400 Then listH = 400
    If listH < 40 Then listH = 40

    Dim frm As New System.Windows.Forms.Form
    Dim ok As Boolean = False

    Try
        frm.Text = "새 부품번호 확인"
        frm.Width = 720
        frm.Height = listH + 166
        frm.StartPosition = System.Windows.Forms.FormStartPosition.CenterScreen
        frm.FormBorderStyle = System.Windows.Forms.FormBorderStyle.FixedDialog
        frm.MinimizeBox = False
        frm.MaximizeBox = False
        frm.TopMost = True

        Dim lbl As New System.Windows.Forms.Label
        lbl.Text = "자동 계산된 새 부품번호입니다. 필요하면 오른쪽 칸에서 수정하세요." & vbCrLf & _
                   "[생성] 을 누르면 바로 리비전을 만듭니다."
        lbl.SetBounds(12, 12, 680, 36)
        frm.Controls.Add(lbl)

        Dim pnl As New System.Windows.Forms.Panel
        pnl.SetBounds(12, 54, 686, listH)
        pnl.AutoScroll = True
        frm.Controls.Add(pnl)

        Dim boxes As New List(Of System.Windows.Forms.TextBox)

        For i As Integer = 0 To n - 1

            Dim src As New System.Windows.Forms.Label
            src.Text = curPNs(i) & "   →"
            src.SetBounds(4, i * rowH + 6, 300, 20)
            pnl.Controls.Add(src)

            Dim tb As New System.Windows.Forms.TextBox
            tb.Text = editPNs(i)
            tb.SetBounds(310, i * rowH + 3, 340, 24)
            pnl.Controls.Add(tb)

            boxes.Add(tb)
        Next

        Dim btnOK As New System.Windows.Forms.Button
        btnOK.Text = "생성"
        btnOK.SetBounds(494, listH + 68, 92, 32)
        btnOK.DialogResult = System.Windows.Forms.DialogResult.OK
        frm.Controls.Add(btnOK)

        Dim btnCancel As New System.Windows.Forms.Button
        btnCancel.Text = "취소"
        btnCancel.SetBounds(598, listH + 68, 92, 32)
        btnCancel.DialogResult = System.Windows.Forms.DialogResult.Cancel
        frm.Controls.Add(btnCancel)

        SetDefaultButtons(frm, btnOK, btnCancel)

        Dim bad As Char() = System.IO.Path.GetInvalidFileNameChars()

        Do
            Dim res As System.Windows.Forms.DialogResult = frm.ShowDialog()
            If res <> System.Windows.Forms.DialogResult.OK Then Exit Do

            Dim vals As New List(Of String)
            Dim err  As String = ""

            For i As Integer = 0 To n - 1
                Dim v As String = boxes(i).Text
                If v Is Nothing Then v = ""
                v = v.Trim()
                If v = "" Then v = autoPNs(i)
                vals.Add(v)
            Next

            For i As Integer = 0 To n - 1

                Dim v As String = vals(i)

                If v = "" Then
                    err &= "· " & curPNs(i) & " : 새 부품번호가 비어 있습니다" & vbCrLf
                    Continue For
                End If

                If v.IndexOfAny(bad) >= 0 Then
                    err &= "· " & v & " : 파일명에 쓸 수 없는 문자가 있습니다" & vbCrLf
                    Continue For
                End If

                If String.Equals(v, curPNs(i), StringComparison.OrdinalIgnoreCase) Then
                    err &= "· " & v & " : 현재 부품번호와 같습니다" & vbCrLf
                    Continue For
                End If

                For j As Integer = 0 To i - 1
                    If String.Equals(v, vals(j), StringComparison.OrdinalIgnoreCase) Then
                        err &= "· " & v & " : 목록 안에서 중복됩니다 (" & (j + 1) & "번, " & (i + 1) & "번)" & vbCrLf
                        Exit For
                    End If
                Next

                Try
                    Dim mDir As String = System.IO.Path.GetDirectoryName(mdlPaths(i))
                    Dim dDir As String = System.IO.Path.GetDirectoryName(drwPaths(i))
                    Dim mExt As String = System.IO.Path.GetExtension(mdlPaths(i))
                    Dim dExt As String = System.IO.Path.GetExtension(drwPaths(i))

                    If System.IO.File.Exists(System.IO.Path.Combine(mDir, v & mExt)) Then
                        err &= "· " & v & mExt & " : 같은 이름의 파일이 이미 있습니다" & vbCrLf
                    End If
                    If System.IO.File.Exists(System.IO.Path.Combine(dDir, v & dExt)) Then
                        err &= "· " & v & dExt & " : 같은 이름의 파일이 이미 있습니다" & vbCrLf
                    End If
                Catch
                    err &= "· " & v & " : 경로를 만들 수 없습니다" & vbCrLf
                End Try

            Next

            If err = "" Then
                For i As Integer = 0 To n - 1
                    editPNs(i) = vals(i)
                Next
                ok = True
                Exit Do
            End If

            MessageBox.Show("아래 항목을 고쳐 주세요." & vbCrLf & vbCrLf & err, _
                            "새 부품번호 확인")
        Loop

    Finally
        frm.Dispose()
    End Try

    Return ok
End Function

Function PickListPre(names As List(Of String), prompt As String, _
                     preChecked As List(Of Boolean)) As List(Of Integer)
    Dim frm As New System.Windows.Forms.Form
    Dim picked As List(Of Integer) = Nothing

    Try
        frm.Text = "리비전 생성"
        frm.Width  = 720
        frm.Height = 480
        frm.StartPosition = System.Windows.Forms.FormStartPosition.CenterScreen
        frm.FormBorderStyle = System.Windows.Forms.FormBorderStyle.FixedDialog
        frm.MinimizeBox = False
        frm.MaximizeBox = False
        frm.TopMost = True

        Dim lbl As New System.Windows.Forms.Label
        lbl.Text = prompt
        lbl.SetBounds(12, 12, 686, 36)

        Dim clb As New System.Windows.Forms.CheckedListBox
        clb.SetBounds(12, 52, 686, 326)
        clb.CheckOnClick = True

        For i As Integer = 0 To names.Count - 1
            Dim ck As Boolean = False
            If preChecked IsNot Nothing AndAlso i < preChecked.Count Then ck = preChecked(i)
            clb.Items.Add(names(i), ck)
        Next


        Dim btnOK As New System.Windows.Forms.Button
        btnOK.Text = "확인"
        btnOK.SetBounds(494, 392, 92, 32)
        btnOK.DialogResult = System.Windows.Forms.DialogResult.OK

        Dim btnCancel As New System.Windows.Forms.Button
        btnCancel.Text = "취소"
        btnCancel.SetBounds(598, 392, 92, 32)
        btnCancel.DialogResult = System.Windows.Forms.DialogResult.Cancel

        frm.Controls.Add(lbl)
        frm.Controls.Add(clb)
        frm.Controls.Add(btnOK)
        frm.Controls.Add(btnCancel)
        SetDefaultButtons(frm, btnOK, btnCancel)

        Dim result As System.Windows.Forms.DialogResult = frm.ShowDialog()

        If result = System.Windows.Forms.DialogResult.OK Then
            picked = New List(Of Integer)
            For Each ix As Integer In clb.CheckedIndices
                picked.Add(ix)
            Next
        End If

    Finally
        frm.Dispose()
    End Try

    Return picked
End Function
